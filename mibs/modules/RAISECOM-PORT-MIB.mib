-- RAISECOM-PORT-MIB
--
-- Generated by mibs/gen_mibs.py; edit the generator, not this file.
-- Unofficial MIB for Raisecom ISCOM2600G switches, written from what
-- an ISCOM2624G-4GE-PWR-AC with software 3.60.311 (ROS 5.2.1) actually returns. Objects marked
-- "Reconstructed" have no published Raisecom MIB.
--

RAISECOM-PORT-MIB DEFINITIONS ::= BEGIN

IMPORTS
    MODULE-IDENTITY,
    OBJECT-TYPE
        FROM SNMPv2-SMI
    DisplayString
        FROM SNMPv2-TC
    MODULE-COMPLIANCE,
    OBJECT-GROUP
        FROM SNMPv2-CONF
    ifIndex
        FROM IF-MIB
    iscomSwitch
        FROM RAISECOM-BASE-MIB;

raisecomPortMIB MODULE-IDENTITY
    LAST-UPDATED "202610210000Z"
    ORGANIZATION "raisecom-snmp-exporter project (unofficial, not a Raisecom publication)"
    CONTACT-INFO
        "See README.md in the raisecom-snmp-exporter repository."
    DESCRIPTION
        "Port configuration of ISCOM switches. Reconstructed from data
         returned by ISCOM2624G-4GE-PWR-AC, software 3.60.311 (ROS
         5.2.1); Raisecom publishes no MIB for this object."
    REVISION     "202610210000Z"
    DESCRIPTION
        "Initial version."
    ::= { iscomSwitch 20 }

raisecomPortObjects OBJECT IDENTIFIER ::= { raisecomPortMIB 1 }

raisecomPortTable OBJECT-TYPE
    SYNTAX      SEQUENCE OF RaisecomPortEntry
    MAX-ACCESS  not-accessible
    STATUS      current
    DESCRIPTION
        "Per-port settings."
    ::= { raisecomPortObjects 1 }

raisecomPortEntry OBJECT-TYPE
    SYNTAX      RaisecomPortEntry
    MAX-ACCESS  not-accessible
    STATUS      current
    DESCRIPTION
        "Settings of one port."
    INDEX       { ifIndex }
    ::= { raisecomPortTable 1 }

RaisecomPortEntry ::= SEQUENCE {
    raisecomPortDescription  DisplayString
}

raisecomPortDescription OBJECT-TYPE
    SYNTAX      DisplayString
    MAX-ACCESS  read-only
    STATUS      current
    DESCRIPTION
        "Description configured on the port (ROS leaves IF-MIB ifAlias
         empty). Reconstructed from data returned by ISCOM2624G-4GE-PWR-
         AC, software 3.60.311 (ROS 5.2.1); Raisecom publishes no MIB for
         this object."
    ::= { raisecomPortEntry 2 }

raisecomPortMIBConformance OBJECT IDENTIFIER ::= { raisecomPortMIB 100 }
raisecomPortMIBGroups OBJECT IDENTIFIER ::= { raisecomPortMIBConformance 1 }
raisecomPortMIBCompliances OBJECT IDENTIFIER ::= { raisecomPortMIBConformance 2 }

raisecomPortMIBGroup OBJECT-GROUP
    OBJECTS {
        raisecomPortDescription
    }
    STATUS      current
    DESCRIPTION
        "Objects of RAISECOM-PORT-MIB."
    ::= { raisecomPortMIBGroups 1 }

raisecomPortMIBCompliance MODULE-COMPLIANCE
    STATUS      current
    DESCRIPTION
        "Devices implementing RAISECOM-PORT-MIB."
    MODULE
        MANDATORY-GROUPS { raisecomPortMIBGroup }
    ::= { raisecomPortMIBCompliances 1 }

END
