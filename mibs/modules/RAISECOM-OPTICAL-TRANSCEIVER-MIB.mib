-- RAISECOM-OPTICAL-TRANSCEIVER-MIB
--
-- Generated by mibs/gen_mibs.py; edit the generator, not this file.
-- Unofficial MIB for Raisecom ISCOM2600G switches, written from what
-- an ISCOM2624G-4GE-PWR-AC with software 3.60.311 (ROS 5.2.1) actually returns. Objects marked
-- "Reconstructed" have no published Raisecom MIB.
--

RAISECOM-OPTICAL-TRANSCEIVER-MIB DEFINITIONS ::= BEGIN

IMPORTS
    Integer32,
    MODULE-IDENTITY,
    OBJECT-TYPE,
    TimeTicks,
    Unsigned32
        FROM SNMPv2-SMI
    TEXTUAL-CONVENTION
        FROM SNMPv2-TC
    MODULE-COMPLIANCE,
    OBJECT-GROUP
        FROM SNMPv2-CONF
    ifIndex
        FROM IF-MIB
    EnableVar,
    raisecomAgent
        FROM RAISECOM-BASE-MIB;

raisecomOpticalTransceiver MODULE-IDENTITY
    LAST-UPDATED "202610210000Z"
    ORGANIZATION "raisecom-snmp-exporter project (unofficial, not a Raisecom publication)"
    CONTACT-INFO
        "See README.md in the raisecom-snmp-exporter repository."
    DESCRIPTION
        "Optical transceiver information and digital diagnostics (DDM) of
         Raisecom ROS devices."
    REVISION     "202610210000Z"
    DESCRIPTION
        "Initial version."
    ::= { raisecomAgent 18 }

OpticalParameterType ::= TEXTUAL-CONVENTION
    STATUS      current
    DESCRIPTION
        "Monitored DDM parameter. The published Raisecom MIB names value
         5 laserTemperature; software 3.60.311 (ROS 5.2.1) returns the
         3.3 V supply voltage there (about 3300 mV with 2900..3600 mV
         thresholds)."
    SYNTAX      INTEGER { transceiverTemperature(1), txBiasCurrent(2), txPower(3), rxPower(4), supplyVoltage(5) }

OpticalParameterValue ::= TEXTUAL-CONVENTION
    DISPLAY-HINT "d-3"
    STATUS      current
    DESCRIPTION
        "DDM value in thousandths of the base unit:
         transceiverTemperature in millidegrees Celsius, txBiasCurrent in
         microamperes, txPower and rxPower in thousandths of dBm,
         supplyVoltage in millivolts. -1000000 means not available."
    SYNTAX      Integer32 (-1000000 | -40000..6553600)

raisecomOpticalTransceiverGlobalEnable OBJECT IDENTIFIER ::= { raisecomOpticalTransceiver 1 }

raisecomOpticalTransceiverNotifyEnable OBJECT-TYPE
    SYNTAX      EnableVar
    MAX-ACCESS  read-write
    STATUS      current
    DESCRIPTION
        "Whether transceiver notifications are sent."
    ::= { raisecomOpticalTransceiverGlobalEnable 1 }

raisecomOpticalTransceiverDDMEnable OBJECT-TYPE
    SYNTAX      EnableVar
    MAX-ACCESS  read-write
    STATUS      current
    DESCRIPTION
        "Whether digital diagnostics monitoring is enabled. DDM values
         are only populated when enabled."
    ::= { raisecomOpticalTransceiverGlobalEnable 2 }

raisecomOpticalTransceiverCheckPwdEnable OBJECT-TYPE
    SYNTAX      EnableVar
    MAX-ACCESS  read-write
    STATUS      current
    DESCRIPTION
        "Whether transceiver password checking is enabled."
    ::= { raisecomOpticalTransceiverGlobalEnable 3 }

raisecomOpticalTransceiverPollInterval OBJECT-TYPE
    SYNTAX      Integer32
    UNITS       "seconds"
    MAX-ACCESS  read-write
    STATUS      current
    DESCRIPTION
        "DDM poll interval."
    ::= { raisecomOpticalTransceiverGlobalEnable 4 }

raisecomOpticalTransceiverObjects OBJECT IDENTIFIER ::= { raisecomOpticalTransceiver 2 }

raisecomOpticalTransceiverInfoGroup OBJECT IDENTIFIER ::= { raisecomOpticalTransceiverObjects 1 }

raisecomOpticalTransceiverInfoTable OBJECT-TYPE
    SYNTAX      SEQUENCE OF RaisecomOpticalTransceiverInfoEntry
    MAX-ACCESS  not-accessible
    STATUS      current
    DESCRIPTION
        "Information about the transceiver in each pluggable port."
    ::= { raisecomOpticalTransceiverInfoGroup 1 }

raisecomOpticalTransceiverInfoEntry OBJECT-TYPE
    SYNTAX      RaisecomOpticalTransceiverInfoEntry
    MAX-ACCESS  not-accessible
    STATUS      current
    DESCRIPTION
        "Transceiver in one port."
    INDEX       { ifIndex }
    ::= { raisecomOpticalTransceiverInfoTable 1 }

RaisecomOpticalTransceiverInfoEntry ::= SEQUENCE {
    raisecomOpticalTransceiverType                  INTEGER,
    raisecomOpticalTransceiverConnectorType         INTEGER,
    raisecomOpticalTransceiverVendorName            OCTET STRING,
    raisecomOpticalTransceiverVendorPN              OCTET STRING,
    raisecomOpticalTransceiverVendorSN              OCTET STRING,
    raisecomOpticalTransceiverMediaType             INTEGER,
    raisecomOpticalTransceiverTransmissionDistance  Integer32,
    raisecomOpticalTransceiverAbility               Unsigned32,
    raisecomOpticalTransceiverDDM                   INTEGER,
    raisecomOpticalTransceiverCalibrationType       INTEGER,
    raisecomOpticalTransceiverRSSI                  INTEGER,
    raisecomOpticalTransceiverVendorRev             OCTET STRING,
    raisecomOpticalTransceiverBRMax                 Integer32,
    raisecomOpticalTransceiverBRMin                 Integer32,
    raisecomOpticalTransceiverWavelengthContrl      INTEGER,
    raisecomOpticalTransceiverWavelength            Integer32,
    raisecomOpticalTransceiverWaveTolerance         Integer32,
    raisecomOpticalTransceiverCompatibility         OCTET STRING,
    raisecomOpticalTransceiverPowerDissipation      INTEGER,
    raisecomOpticalTransceiverCDR                   INTEGER,
    raisecomOpticalTransceiverRefClock              INTEGER,
    raisecomOpticalTransceiverTransmitterType       INTEGER,
    raisecomOpticalTransceiverCooled                INTEGER,
    raisecomOpticalTransceiverTunalbe               INTEGER,
    raisecomOpticalTransceiverDetectorType          INTEGER,
    raisecomOpticalTransceiverLineLoopBack          INTEGER,
    raisecomOpticalTransceiverXFILoopBack           INTEGER,
    raisecomOpticalTransceiverVps                   INTEGER,
    raisecomOpticalTransceiverTxDis                 INTEGER,
    raisecomOpticalTransceiverStandby               INTEGER,
    raisecomOpticalTransceiverInVpsLowPower         INTEGER,
    raisecomOpticalTransceiverOutVpsLowPower        INTEGER,
    raisecomOpticalTransceiverFEC                   INTEGER,
    raisecomOpticalTransceiverCMU                   INTEGER
}

raisecomOpticalTransceiverType OBJECT-TYPE
    SYNTAX      INTEGER { unknown(1), gbic(2), soldered(3), sfp(4), xbi(5), xenpak(6), xfp(7), xff(8), xfpE(9), xpak(10), x2(11), sfpj(12) }
    MAX-ACCESS  read-only
    STATUS      current
    DESCRIPTION
        "Physical type of the transceiver."
    ::= { raisecomOpticalTransceiverInfoEntry 1 }

raisecomOpticalTransceiverConnectorType OBJECT-TYPE
    SYNTAX      INTEGER { unknown(0), sc(1), db9(2), hssdc(3), bncTnc(4), fiberCoaxialHead(5), fiberJack(6), lc(7), mtRj(8), mu(9), sg(10), fiberPigtail(11), mpoParallelOptic(12), hssdcII(20), copper(21), rj45(22) }
    MAX-ACCESS  read-only
    STATUS      current
    DESCRIPTION
        "Connector type."
    ::= { raisecomOpticalTransceiverInfoEntry 2 }

raisecomOpticalTransceiverVendorName OBJECT-TYPE
    SYNTAX      OCTET STRING (SIZE (0..32))
    MAX-ACCESS  read-only
    STATUS      current
    DESCRIPTION
        "Vendor name (space padded)."
    ::= { raisecomOpticalTransceiverInfoEntry 3 }

raisecomOpticalTransceiverVendorPN OBJECT-TYPE
    SYNTAX      OCTET STRING (SIZE (0..32))
    MAX-ACCESS  read-only
    STATUS      current
    DESCRIPTION
        "Vendor part number (space padded)."
    ::= { raisecomOpticalTransceiverInfoEntry 4 }

raisecomOpticalTransceiverVendorSN OBJECT-TYPE
    SYNTAX      OCTET STRING (SIZE (0..32))
    MAX-ACCESS  read-only
    STATUS      current
    DESCRIPTION
        "Vendor serial number (space padded)."
    ::= { raisecomOpticalTransceiverInfoEntry 5 }

raisecomOpticalTransceiverMediaType OBJECT-TYPE
    SYNTAX      INTEGER { singleMode(1), multiModeE50(2), multiMode50(3), multiMode625(4), copper(5), singleModeKm(6), multiModeOM3(7) }
    MAX-ACCESS  read-only
    STATUS      current
    DESCRIPTION
        "Fiber or cable type."
    ::= { raisecomOpticalTransceiverInfoEntry 6 }

raisecomOpticalTransceiverTransmissionDistance OBJECT-TYPE
    SYNTAX      Integer32
    UNITS       "meters"
    MAX-ACCESS  read-only
    STATUS      current
    DESCRIPTION
        "Maximum transmission distance."
    ::= { raisecomOpticalTransceiverInfoEntry 7 }

raisecomOpticalTransceiverAbility OBJECT-TYPE
    SYNTAX      Unsigned32
    MAX-ACCESS  read-only
    STATUS      current
    DESCRIPTION
        "Bit mask of the DDM parameters the module supports."
    ::= { raisecomOpticalTransceiverInfoEntry 8 }

raisecomOpticalTransceiverDDM OBJECT-TYPE
    SYNTAX      INTEGER { support(1), notSupport(2) }
    MAX-ACCESS  read-only
    STATUS      current
    DESCRIPTION
        "Whether the module supports digital diagnostics."
    ::= { raisecomOpticalTransceiverInfoEntry 9 }

raisecomOpticalTransceiverCalibrationType OBJECT-TYPE
    SYNTAX      INTEGER { unknown(1), internal(2), external(3) }
    MAX-ACCESS  read-only
    STATUS      current
    DESCRIPTION
        "DDM calibration type."
    ::= { raisecomOpticalTransceiverInfoEntry 10 }

raisecomOpticalTransceiverRSSI OBJECT-TYPE
    SYNTAX      INTEGER { support(1), notSupport(2) }
    MAX-ACCESS  read-only
    STATUS      current
    DESCRIPTION
        "Whether the module supports RSSI."
    ::= { raisecomOpticalTransceiverInfoEntry 11 }

raisecomOpticalTransceiverVendorRev OBJECT-TYPE
    SYNTAX      OCTET STRING (SIZE (0..16))
    MAX-ACCESS  read-only
    STATUS      current
    DESCRIPTION
        "Vendor revision."
    ::= { raisecomOpticalTransceiverInfoEntry 12 }

raisecomOpticalTransceiverBRMax OBJECT-TYPE
    SYNTAX      Integer32
    UNITS       "Mbps"
    MAX-ACCESS  read-only
    STATUS      current
    DESCRIPTION
        "Maximum bit rate."
    ::= { raisecomOpticalTransceiverInfoEntry 13 }

raisecomOpticalTransceiverBRMin OBJECT-TYPE
    SYNTAX      Integer32
    UNITS       "Mbps"
    MAX-ACCESS  read-only
    STATUS      current
    DESCRIPTION
        "Minimum bit rate."
    ::= { raisecomOpticalTransceiverInfoEntry 14 }

raisecomOpticalTransceiverWavelengthContrl OBJECT-TYPE
    SYNTAX      INTEGER { support(1), notSupport(2) }
    MAX-ACCESS  read-only
    STATUS      current
    DESCRIPTION
        "Whether wavelength control is supported."
    ::= { raisecomOpticalTransceiverInfoEntry 15 }

raisecomOpticalTransceiverWavelength OBJECT-TYPE
    SYNTAX      Integer32
    UNITS       "nm"
    MAX-ACCESS  read-only
    STATUS      current
    DESCRIPTION
        "Nominal laser wavelength. The published MIB says picometres;
         software 3.60.311 (ROS 5.2.1) returns nanometres (e.g. 1310)."
    ::= { raisecomOpticalTransceiverInfoEntry 16 }

raisecomOpticalTransceiverWaveTolerance OBJECT-TYPE
    SYNTAX      Integer32
    MAX-ACCESS  read-only
    STATUS      current
    DESCRIPTION
        "Wavelength tolerance. The published MIB types this OCTET STRING;
         software 3.60.311 (ROS 5.2.1) returns INTEGER."
    ::= { raisecomOpticalTransceiverInfoEntry 17 }

raisecomOpticalTransceiverCompatibility OBJECT-TYPE
    SYNTAX      OCTET STRING (SIZE (0..32))
    MAX-ACCESS  read-only
    STATUS      current
    DESCRIPTION
        "Compatibility code, e.g. 10GBASE-SR."
    ::= { raisecomOpticalTransceiverInfoEntry 18 }

raisecomOpticalTransceiverPowerDissipation OBJECT-TYPE
    SYNTAX      INTEGER { unknown(0), p1W5(1), p2W5(2), p3W5(3), exceed(4) }
    MAX-ACCESS  read-only
    STATUS      current
    DESCRIPTION
        "Power class. software 3.60.311 (ROS 5.2.1) returns unknown(0)
         for SFPs."
    ::= { raisecomOpticalTransceiverInfoEntry 19 }

raisecomOpticalTransceiverCDR OBJECT-TYPE
    SYNTAX      INTEGER { support(1), notSupport(2) }
    MAX-ACCESS  read-only
    STATUS      current
    DESCRIPTION
        "Whether the module has clock and data recovery."
    ::= { raisecomOpticalTransceiverInfoEntry 20 }

raisecomOpticalTransceiverRefClock OBJECT-TYPE
    SYNTAX      INTEGER { required(1), notRequired(2) }
    MAX-ACCESS  read-only
    STATUS      current
    DESCRIPTION
        "Whether a reference clock is required."
    ::= { raisecomOpticalTransceiverInfoEntry 21 }

raisecomOpticalTransceiverTransmitterType OBJECT-TYPE
    SYNTAX      INTEGER { vcsel850nm(1), vcsel1310nm(2), vcsel1550nm(3), fp1310nm(4), dfb1310nm(5), dfb1550nm(6), eml1310nm(7), eml1550nm(8), copperOthers(9) }
    MAX-ACCESS  read-only
    STATUS      current
    DESCRIPTION
        "Transmitter technology."
    ::= { raisecomOpticalTransceiverInfoEntry 22 }

raisecomOpticalTransceiverCooled OBJECT-TYPE
    SYNTAX      INTEGER { cooled(1), uncooled(2) }
    MAX-ACCESS  read-only
    STATUS      current
    DESCRIPTION
        "Whether the laser is cooled."
    ::= { raisecomOpticalTransceiverInfoEntry 24 }

raisecomOpticalTransceiverTunalbe OBJECT-TYPE
    SYNTAX      INTEGER { tunable(1), untunable(2) }
    MAX-ACCESS  read-only
    STATUS      current
    DESCRIPTION
        "Whether the laser is tunable."
    ::= { raisecomOpticalTransceiverInfoEntry 25 }

raisecomOpticalTransceiverDetectorType OBJECT-TYPE
    SYNTAX      INTEGER { pin(1), apd(2) }
    MAX-ACCESS  read-only
    STATUS      current
    DESCRIPTION
        "Receiver detector type."
    ::= { raisecomOpticalTransceiverInfoEntry 26 }

raisecomOpticalTransceiverLineLoopBack OBJECT-TYPE
    SYNTAX      INTEGER { support(1), notSupport(2) }
    MAX-ACCESS  read-only
    STATUS      current
    DESCRIPTION
        "Line loopback support."
    ::= { raisecomOpticalTransceiverInfoEntry 27 }

raisecomOpticalTransceiverXFILoopBack OBJECT-TYPE
    SYNTAX      INTEGER { support(1), notSupport(2) }
    MAX-ACCESS  read-only
    STATUS      current
    DESCRIPTION
        "XFI loopback support."
    ::= { raisecomOpticalTransceiverInfoEntry 28 }

raisecomOpticalTransceiverVps OBJECT-TYPE
    SYNTAX      INTEGER { support(1), notSupport(2) }
    MAX-ACCESS  read-only
    STATUS      current
    DESCRIPTION
        "Variable power supply support."
    ::= { raisecomOpticalTransceiverInfoEntry 29 }

raisecomOpticalTransceiverTxDis OBJECT-TYPE
    SYNTAX      INTEGER { support(1), notSupport(2) }
    MAX-ACCESS  read-only
    STATUS      current
    DESCRIPTION
        "Transmitter disable support."
    ::= { raisecomOpticalTransceiverInfoEntry 30 }

raisecomOpticalTransceiverStandby OBJECT-TYPE
    SYNTAX      INTEGER { support(1), notSupport(2) }
    MAX-ACCESS  read-only
    STATUS      current
    DESCRIPTION
        "Standby mode support."
    ::= { raisecomOpticalTransceiverInfoEntry 31 }

raisecomOpticalTransceiverInVpsLowPower OBJECT-TYPE
    SYNTAX      INTEGER { support(1), notSupport(2) }
    MAX-ACCESS  read-only
    STATUS      current
    DESCRIPTION
        "Low power mode support inside VPS."
    ::= { raisecomOpticalTransceiverInfoEntry 32 }

raisecomOpticalTransceiverOutVpsLowPower OBJECT-TYPE
    SYNTAX      INTEGER { support(1), notSupport(2) }
    MAX-ACCESS  read-only
    STATUS      current
    DESCRIPTION
        "Low power mode support outside VPS."
    ::= { raisecomOpticalTransceiverInfoEntry 33 }

raisecomOpticalTransceiverFEC OBJECT-TYPE
    SYNTAX      INTEGER { support(1), notSupport(2) }
    MAX-ACCESS  read-only
    STATUS      current
    DESCRIPTION
        "Forward error correction support."
    ::= { raisecomOpticalTransceiverInfoEntry 34 }

raisecomOpticalTransceiverCMU OBJECT-TYPE
    SYNTAX      INTEGER { support(1), notSupport(2) }
    MAX-ACCESS  read-only
    STATUS      current
    DESCRIPTION
        "Clock multiplier unit support."
    ::= { raisecomOpticalTransceiverInfoEntry 35 }

raisecomOpticalTransceiverDDMGroup OBJECT IDENTIFIER ::= { raisecomOpticalTransceiverObjects 2 }

raisecomOpticalTransceiverDDMTable OBJECT-TYPE
    SYNTAX      SEQUENCE OF RaisecomOpticalTransceiverDDMEntry
    MAX-ACCESS  not-accessible
    STATUS      current
    DESCRIPTION
        "Digital diagnostics of each transceiver parameter. Rows of
         modules without DDM support contain zeros."
    ::= { raisecomOpticalTransceiverDDMGroup 1 }

raisecomOpticalTransceiverDDMEntry OBJECT-TYPE
    SYNTAX      RaisecomOpticalTransceiverDDMEntry
    MAX-ACCESS  not-accessible
    STATUS      current
    DESCRIPTION
        "One monitored parameter of one transceiver."
    INDEX       { ifIndex, raisecomOpticalTransceiverParameterType }
    ::= { raisecomOpticalTransceiverDDMTable 1 }

RaisecomOpticalTransceiverDDMEntry ::= SEQUENCE {
    raisecomOpticalTransceiverParameterType           OpticalParameterType,
    raisecomOpticalTransceiverParameterValue          OpticalParameterValue,
    raisecomOpticalTransceiverParamHighAlarmThresh    OpticalParameterValue,
    raisecomOpticalTransceiverParamHighWarningThresh  OpticalParameterValue,
    raisecomOpticalTransceiverParamLowAlarmThresh     OpticalParameterValue,
    raisecomOpticalTransceiverParamLowWarningThresh   OpticalParameterValue,
    raisecomOpticalTransceiverParamAlarmStatus        INTEGER,
    raisecomOpticalTransceiverParamAlarmLastValue     OpticalParameterValue,
    raisecomOpticalTransceiverParamAlarmLastChange    TimeTicks,
    raisecomOpticalTransceiverDDM15MinValidIntervals  Unsigned32,
    raisecomOpticalTransceiverDDM24HrValidIntervals   Unsigned32,
    raisecomOpticalTransceiverDDMValidStatus          INTEGER
}

raisecomOpticalTransceiverParameterType OBJECT-TYPE
    SYNTAX      OpticalParameterType
    MAX-ACCESS  not-accessible
    STATUS      current
    DESCRIPTION
        "Monitored parameter."
    ::= { raisecomOpticalTransceiverDDMEntry 1 }

raisecomOpticalTransceiverParameterValue OBJECT-TYPE
    SYNTAX      OpticalParameterValue
    MAX-ACCESS  read-only
    STATUS      current
    DESCRIPTION
        "Current value."
    ::= { raisecomOpticalTransceiverDDMEntry 2 }

raisecomOpticalTransceiverParamHighAlarmThresh OBJECT-TYPE
    SYNTAX      OpticalParameterValue
    MAX-ACCESS  read-only
    STATUS      current
    DESCRIPTION
        "High alarm threshold."
    ::= { raisecomOpticalTransceiverDDMEntry 3 }

raisecomOpticalTransceiverParamHighWarningThresh OBJECT-TYPE
    SYNTAX      OpticalParameterValue
    MAX-ACCESS  read-only
    STATUS      current
    DESCRIPTION
        "High warning threshold."
    ::= { raisecomOpticalTransceiverDDMEntry 4 }

raisecomOpticalTransceiverParamLowAlarmThresh OBJECT-TYPE
    SYNTAX      OpticalParameterValue
    MAX-ACCESS  read-only
    STATUS      current
    DESCRIPTION
        "Low alarm threshold."
    ::= { raisecomOpticalTransceiverDDMEntry 5 }

raisecomOpticalTransceiverParamLowWarningThresh OBJECT-TYPE
    SYNTAX      OpticalParameterValue
    MAX-ACCESS  read-only
    STATUS      current
    DESCRIPTION
        "Low warning threshold."
    ::= { raisecomOpticalTransceiverDDMEntry 6 }

raisecomOpticalTransceiverParamAlarmStatus OBJECT-TYPE
    SYNTAX      INTEGER { unknown(0), normal(1), highAlarm(2), highWarning(3), lowAlarm(4), lowWarning(5) }
    MAX-ACCESS  read-only
    STATUS      current
    DESCRIPTION
        "Current threshold state."
    ::= { raisecomOpticalTransceiverDDMEntry 7 }

raisecomOpticalTransceiverParamAlarmLastValue OBJECT-TYPE
    SYNTAX      OpticalParameterValue
    MAX-ACCESS  read-only
    STATUS      current
    DESCRIPTION
        "Value when the last alarm was raised."
    ::= { raisecomOpticalTransceiverDDMEntry 8 }

raisecomOpticalTransceiverParamAlarmLastChange OBJECT-TYPE
    SYNTAX      TimeTicks
    MAX-ACCESS  read-only
    STATUS      current
    DESCRIPTION
        "sysUpTime when the alarm status last changed."
    ::= { raisecomOpticalTransceiverDDMEntry 9 }

raisecomOpticalTransceiverDDM15MinValidIntervals OBJECT-TYPE
    SYNTAX      Unsigned32 (0..96)
    MAX-ACCESS  read-only
    STATUS      current
    DESCRIPTION
        "Number of valid 15-minute history intervals."
    ::= { raisecomOpticalTransceiverDDMEntry 10 }

raisecomOpticalTransceiverDDM24HrValidIntervals OBJECT-TYPE
    SYNTAX      Unsigned32 (0..7)
    MAX-ACCESS  read-only
    STATUS      current
    DESCRIPTION
        "Number of valid 24-hour history intervals."
    ::= { raisecomOpticalTransceiverDDMEntry 11 }

raisecomOpticalTransceiverDDMValidStatus OBJECT-TYPE
    SYNTAX      INTEGER { unknown(0), valid(1), invalid(2) }
    MAX-ACCESS  read-only
    STATUS      current
    DESCRIPTION
        "Whether the current value is valid."
    ::= { raisecomOpticalTransceiverDDMEntry 12 }

raisecomOpticalTransceiverConformance OBJECT IDENTIFIER ::= { raisecomOpticalTransceiver 100 }
raisecomOpticalTransceiverGroups OBJECT IDENTIFIER ::= { raisecomOpticalTransceiverConformance 1 }
raisecomOpticalTransceiverCompliances OBJECT IDENTIFIER ::= { raisecomOpticalTransceiverConformance 2 }

raisecomOpticalTransceiverGroup OBJECT-GROUP
    OBJECTS {
        raisecomOpticalTransceiverNotifyEnable,
        raisecomOpticalTransceiverDDMEnable,
        raisecomOpticalTransceiverCheckPwdEnable,
        raisecomOpticalTransceiverPollInterval,
        raisecomOpticalTransceiverType,
        raisecomOpticalTransceiverConnectorType,
        raisecomOpticalTransceiverVendorName,
        raisecomOpticalTransceiverVendorPN,
        raisecomOpticalTransceiverVendorSN,
        raisecomOpticalTransceiverMediaType,
        raisecomOpticalTransceiverTransmissionDistance,
        raisecomOpticalTransceiverAbility,
        raisecomOpticalTransceiverDDM,
        raisecomOpticalTransceiverCalibrationType,
        raisecomOpticalTransceiverRSSI,
        raisecomOpticalTransceiverVendorRev,
        raisecomOpticalTransceiverBRMax,
        raisecomOpticalTransceiverBRMin,
        raisecomOpticalTransceiverWavelengthContrl,
        raisecomOpticalTransceiverWavelength,
        raisecomOpticalTransceiverWaveTolerance,
        raisecomOpticalTransceiverCompatibility,
        raisecomOpticalTransceiverPowerDissipation,
        raisecomOpticalTransceiverCDR,
        raisecomOpticalTransceiverRefClock,
        raisecomOpticalTransceiverTransmitterType,
        raisecomOpticalTransceiverCooled,
        raisecomOpticalTransceiverTunalbe,
        raisecomOpticalTransceiverDetectorType,
        raisecomOpticalTransceiverLineLoopBack,
        raisecomOpticalTransceiverXFILoopBack,
        raisecomOpticalTransceiverVps,
        raisecomOpticalTransceiverTxDis,
        raisecomOpticalTransceiverStandby,
        raisecomOpticalTransceiverInVpsLowPower,
        raisecomOpticalTransceiverOutVpsLowPower,
        raisecomOpticalTransceiverFEC,
        raisecomOpticalTransceiverCMU,
        raisecomOpticalTransceiverParameterValue,
        raisecomOpticalTransceiverParamHighAlarmThresh,
        raisecomOpticalTransceiverParamHighWarningThresh,
        raisecomOpticalTransceiverParamLowAlarmThresh,
        raisecomOpticalTransceiverParamLowWarningThresh,
        raisecomOpticalTransceiverParamAlarmStatus,
        raisecomOpticalTransceiverParamAlarmLastValue,
        raisecomOpticalTransceiverParamAlarmLastChange,
        raisecomOpticalTransceiverDDM15MinValidIntervals,
        raisecomOpticalTransceiverDDM24HrValidIntervals,
        raisecomOpticalTransceiverDDMValidStatus
    }
    STATUS      current
    DESCRIPTION
        "Objects of RAISECOM-OPTICAL-TRANSCEIVER-MIB."
    ::= { raisecomOpticalTransceiverGroups 1 }

raisecomOpticalTransceiverCompliance MODULE-COMPLIANCE
    STATUS      current
    DESCRIPTION
        "Devices implementing RAISECOM-OPTICAL-TRANSCEIVER-MIB."
    MODULE
        MANDATORY-GROUPS { raisecomOpticalTransceiverGroup }
    ::= { raisecomOpticalTransceiverCompliances 1 }

END
