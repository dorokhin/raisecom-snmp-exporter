-- RAISECOM-SYSTEM-MIB
--
-- Generated by mibs/gen_mibs.py; edit the generator, not this file.
-- Unofficial MIB for Raisecom ISCOM2600G switches, written from what
-- an ISCOM2624G-4GE-PWR-AC with software 3.60.311 (ROS 5.2.1) actually returns. Objects marked
-- "Reconstructed" have no published Raisecom MIB.
--

RAISECOM-SYSTEM-MIB DEFINITIONS ::= BEGIN

IMPORTS
    Integer32,
    MODULE-IDENTITY,
    OBJECT-TYPE
        FROM SNMPv2-SMI
    MODULE-COMPLIANCE,
    OBJECT-GROUP
        FROM SNMPv2-CONF
    EnableVar,
    raisecomAgent
        FROM RAISECOM-BASE-MIB;

raisecomSystem MODULE-IDENTITY
    LAST-UPDATED "202610210000Z"
    ORGANIZATION "raisecom-snmp-exporter project (unofficial, not a Raisecom publication)"
    CONTACT-INFO
        "See README.md in the raisecom-snmp-exporter repository."
    DESCRIPTION
        "CPU, memory and temperature of Raisecom ROS devices, laid out as
         software 3.60.311 (ROS 5.2.1) serves them."
    REVISION     "202610210000Z"
    DESCRIPTION
        "Initial version."
    ::= { raisecomAgent 1 }

raisecomCpu OBJECT IDENTIFIER ::= { raisecomSystem 1 }

raisecomCPUTableGroup OBJECT IDENTIFIER ::= { raisecomCpu 5 }

raisecomCPUUtilizationGroup OBJECT IDENTIFIER ::= { raisecomCPUTableGroup 1 }

raisecomTotalCPUUtilizationTable OBJECT-TYPE
    SYNTAX      SEQUENCE OF RaisecomTotalCPUUtilizationEntry
    MAX-ACCESS  not-accessible
    STATUS      current
    DESCRIPTION
        "Total CPU utilization per averaging period. Position verified on
         software 3.60.311 (ROS 5.2.1), where it differs from the
         published Raisecom MIB."
    ::= { raisecomCPUUtilizationGroup 4 }

raisecomTotalCPUUtilizationEntry OBJECT-TYPE
    SYNTAX      RaisecomTotalCPUUtilizationEntry
    MAX-ACCESS  not-accessible
    STATUS      current
    DESCRIPTION
        "CPU utilization for one period."
    INDEX       { raisecomTotalCPUPeriod }
    ::= { raisecomTotalCPUUtilizationTable 1 }

RaisecomTotalCPUUtilizationEntry ::= SEQUENCE {
    raisecomTotalCPUPeriod       INTEGER,
    raisecomTotalCPUUtilization  Integer32
}

raisecomTotalCPUPeriod OBJECT-TYPE
    SYNTAX      INTEGER { oneSec(1), fiveSec(2), oneMin(3), tenMin(4), twoHour(5) }
    MAX-ACCESS  not-accessible
    STATUS      current
    DESCRIPTION
        "Period over which CPU utilization is averaged."
    ::= { raisecomTotalCPUUtilizationEntry 1 }

raisecomTotalCPUUtilization OBJECT-TYPE
    SYNTAX      Integer32 (0..100)
    UNITS       "percent"
    MAX-ACCESS  read-only
    STATUS      current
    DESCRIPTION
        "CPU busy percentage over the period."
    ::= { raisecomTotalCPUUtilizationEntry 2 }

raisecomMemory OBJECT IDENTIFIER ::= { raisecomSystem 3 }

raisecomMemoryTotal OBJECT-TYPE
    SYNTAX      Integer32
    UNITS       "bytes"
    MAX-ACCESS  read-only
    STATUS      current
    DESCRIPTION
        "Total memory of the system. Position verified on software
         3.60.311 (ROS 5.2.1), where it differs from the published
         Raisecom MIB."
    ::= { raisecomMemory 1 }

raisecomMemoryAvailable OBJECT-TYPE
    SYNTAX      Integer32
    UNITS       "bytes"
    MAX-ACCESS  read-only
    STATUS      current
    DESCRIPTION
        "Available memory of the system."
    ::= { raisecomMemory 2 }

raisecomMemoryUtil OBJECT-TYPE
    SYNTAX      Integer32 (0..100)
    UNITS       "percent"
    MAX-ACCESS  read-only
    STATUS      current
    DESCRIPTION
        "Current memory utilization. The published MIB types this OCTET
         STRING; software 3.60.311 (ROS 5.2.1) returns INTEGER."
    ::= { raisecomMemory 3 }

raisecomMemoryTrapEnable OBJECT-TYPE
    SYNTAX      EnableVar
    MAX-ACCESS  read-write
    STATUS      current
    DESCRIPTION
        "Whether the memory trap is enabled."
    ::= { raisecomMemory 4 }

raisecomMemoryThrshd OBJECT-TYPE
    SYNTAX      Integer32 (0..100)
    UNITS       "percent"
    MAX-ACCESS  read-write
    STATUS      current
    DESCRIPTION
        "Memory utilization alarm threshold."
    ::= { raisecomMemory 5 }

raisecomMemoryThrshdRecover OBJECT-TYPE
    SYNTAX      Integer32 (0..100)
    UNITS       "percent"
    MAX-ACCESS  read-write
    STATUS      current
    DESCRIPTION
        "Memory utilization at which the alarm clears."
    ::= { raisecomMemory 6 }

raisecomMemoryMonInterval OBJECT-TYPE
    SYNTAX      Integer32
    UNITS       "seconds"
    MAX-ACCESS  read-write
    STATUS      current
    DESCRIPTION
        "Memory monitor interval."
    ::= { raisecomMemory 7 }

raisecomInformation OBJECT IDENTIFIER ::= { raisecomSystem 4 }

raisecomTemperature OBJECT IDENTIFIER ::= { raisecomInformation 2 }

raisecomTemperatureValue OBJECT-TYPE
    SYNTAX      Integer32
    UNITS       "degrees Celsius"
    MAX-ACCESS  read-only
    STATUS      current
    DESCRIPTION
        "Current board temperature."
    ::= { raisecomTemperature 1 }

raisecomTemperatureMin OBJECT-TYPE
    SYNTAX      Integer32
    UNITS       "degrees Celsius"
    MAX-ACCESS  read-only
    STATUS      current
    DESCRIPTION
        "Lowest temperature since boot."
    ::= { raisecomTemperature 2 }

raisecomTemperatureMax OBJECT-TYPE
    SYNTAX      Integer32
    UNITS       "degrees Celsius"
    MAX-ACCESS  read-only
    STATUS      current
    DESCRIPTION
        "Highest temperature since boot."
    ::= { raisecomTemperature 3 }

raisecomTemperatureTrapEnable OBJECT-TYPE
    SYNTAX      EnableVar
    MAX-ACCESS  read-write
    STATUS      current
    DESCRIPTION
        "Whether the temperature trap is enabled."
    ::= { raisecomTemperature 4 }

raisecomTemperatureThresholdLow OBJECT-TYPE
    SYNTAX      Integer32
    UNITS       "degrees Celsius"
    MAX-ACCESS  read-write
    STATUS      current
    DESCRIPTION
        "Low temperature alarm threshold."
    ::= { raisecomTemperature 5 }

raisecomTemperatureThresholdHigh OBJECT-TYPE
    SYNTAX      Integer32
    UNITS       "degrees Celsius"
    MAX-ACCESS  read-write
    STATUS      current
    DESCRIPTION
        "High temperature alarm threshold."
    ::= { raisecomTemperature 6 }

raisecomTemperatureTrapTimes OBJECT-TYPE
    SYNTAX      Integer32
    MAX-ACCESS  read-only
    STATUS      current
    DESCRIPTION
        "Number of abnormal temperature events."
    ::= { raisecomTemperature 7 }

raisecomTemperatureHighTimes OBJECT-TYPE
    SYNTAX      Integer32
    MAX-ACCESS  read-only
    STATUS      current
    DESCRIPTION
        "Number of high temperature events."
    ::= { raisecomTemperature 8 }

raisecomTemperatureLowTimes OBJECT-TYPE
    SYNTAX      Integer32
    MAX-ACCESS  read-only
    STATUS      current
    DESCRIPTION
        "Number of low temperature events."
    ::= { raisecomTemperature 9 }

raisecomSystemConformance OBJECT IDENTIFIER ::= { raisecomSystem 100 }
raisecomSystemGroups OBJECT IDENTIFIER ::= { raisecomSystemConformance 1 }
raisecomSystemCompliances OBJECT IDENTIFIER ::= { raisecomSystemConformance 2 }

raisecomSystemGroup OBJECT-GROUP
    OBJECTS {
        raisecomTotalCPUUtilization,
        raisecomMemoryTotal,
        raisecomMemoryAvailable,
        raisecomMemoryUtil,
        raisecomMemoryTrapEnable,
        raisecomMemoryThrshd,
        raisecomMemoryThrshdRecover,
        raisecomMemoryMonInterval,
        raisecomTemperatureValue,
        raisecomTemperatureMin,
        raisecomTemperatureMax,
        raisecomTemperatureTrapEnable,
        raisecomTemperatureThresholdLow,
        raisecomTemperatureThresholdHigh,
        raisecomTemperatureTrapTimes,
        raisecomTemperatureHighTimes,
        raisecomTemperatureLowTimes
    }
    STATUS      current
    DESCRIPTION
        "Objects of RAISECOM-SYSTEM-MIB."
    ::= { raisecomSystemGroups 1 }

raisecomSystemCompliance MODULE-COMPLIANCE
    STATUS      current
    DESCRIPTION
        "Devices implementing RAISECOM-SYSTEM-MIB."
    MODULE
        MANDATORY-GROUPS { raisecomSystemGroup }
    ::= { raisecomSystemCompliances 1 }

END
