-- RAISECOM-DEVICE-MIB
--
-- Generated by mibs/gen_mibs.py; edit the generator, not this file.
-- Unofficial MIB for Raisecom ISCOM2600G switches, written from what
-- an ISCOM2624G-4GE-PWR-AC with software 3.60.311 (ROS 5.2.1) actually returns. Objects marked
-- "Reconstructed" have no published Raisecom MIB.
--

RAISECOM-DEVICE-MIB DEFINITIONS ::= BEGIN

IMPORTS
    Integer32,
    MODULE-IDENTITY,
    OBJECT-TYPE
        FROM SNMPv2-SMI
    DisplayString,
    MacAddress
        FROM SNMPv2-TC
    MODULE-COMPLIANCE,
    OBJECT-GROUP
        FROM SNMPv2-CONF
    iscomSwitch
        FROM RAISECOM-BASE-MIB;

raisecomDeviceMIB MODULE-IDENTITY
    LAST-UPDATED "202610210000Z"
    ORGANIZATION "raisecom-snmp-exporter project (unofficial, not a Raisecom publication)"
    CONTACT-INFO
        "See README.md in the raisecom-snmp-exporter repository."
    DESCRIPTION
        "Identification of ISCOM switches. Reconstructed from data
         returned by ISCOM2624G-4GE-PWR-AC, software 3.60.311 (ROS
         5.2.1); Raisecom publishes no MIB for this object."
    REVISION     "202610210000Z"
    DESCRIPTION
        "Initial version."
    ::= { iscomSwitch 1 }

raisecomDeviceInfo OBJECT IDENTIFIER ::= { raisecomDeviceMIB 1 }

raisecomDeviceSoftwareVersion OBJECT-TYPE
    SYNTAX      DisplayString
    MAX-ACCESS  read-only
    STATUS      current
    DESCRIPTION
        "Software version, e.g. 3.60.311(Compiled Mar 25 2020 18:40:44).
         Reconstructed from data returned by ISCOM2624G-4GE-PWR-AC,
         software 3.60.311 (ROS 5.2.1); Raisecom publishes no MIB for
         this object."
    ::= { raisecomDeviceInfo 1 }

raisecomDeviceHardwareVersion OBJECT-TYPE
    SYNTAX      DisplayString
    MAX-ACCESS  read-only
    STATUS      current
    DESCRIPTION
        "Hardware version, e.g. A.01. Reconstructed from data returned by
         ISCOM2624G-4GE-PWR-AC, software 3.60.311 (ROS 5.2.1); Raisecom
         publishes no MIB for this object."
    ::= { raisecomDeviceInfo 2 }

raisecomDevicePortNumber OBJECT-TYPE
    SYNTAX      Integer32
    MAX-ACCESS  read-only
    STATUS      current
    DESCRIPTION
        "Number of interfaces (equals ifNumber on the reference device).
         Reconstructed from data returned by ISCOM2624G-4GE-PWR-AC,
         software 3.60.311 (ROS 5.2.1); Raisecom publishes no MIB for
         this object."
    ::= { raisecomDeviceInfo 5 }

raisecomDeviceMacAddress OBJECT-TYPE
    SYNTAX      MacAddress
    MAX-ACCESS  read-only
    STATUS      current
    DESCRIPTION
        "System MAC address. Reconstructed from data returned by
         ISCOM2624G-4GE-PWR-AC, software 3.60.311 (ROS 5.2.1); Raisecom
         publishes no MIB for this object."
    ::= { raisecomDeviceInfo 9 }

raisecomDeviceBootromVersion OBJECT-TYPE
    SYNTAX      DisplayString
    MAX-ACCESS  read-only
    STATUS      current
    DESCRIPTION
        "Bootrom version. Reconstructed from data returned by
         ISCOM2624G-4GE-PWR-AC, software 3.60.311 (ROS 5.2.1); Raisecom
         publishes no MIB for this object."
    ::= { raisecomDeviceInfo 13 }

raisecomDeviceSerialNumber OBJECT-TYPE
    SYNTAX      DisplayString
    MAX-ACCESS  read-only
    STATUS      current
    DESCRIPTION
        "Serial number. Reconstructed from data returned by
         ISCOM2624G-4GE-PWR-AC, software 3.60.311 (ROS 5.2.1); Raisecom
         publishes no MIB for this object."
    ::= { raisecomDeviceInfo 14 }

raisecomDeviceDescription OBJECT-TYPE
    SYNTAX      DisplayString
    MAX-ACCESS  read-only
    STATUS      current
    DESCRIPTION
        "Model and software version, e.g. ISCOM2624G-4GE-PWR-AC 3.60.311.
         Reconstructed from data returned by ISCOM2624G-4GE-PWR-AC,
         software 3.60.311 (ROS 5.2.1); Raisecom publishes no MIB for
         this object."
    ::= { raisecomDeviceInfo 16 }

raisecomDeviceVendor OBJECT-TYPE
    SYNTAX      DisplayString
    MAX-ACCESS  read-only
    STATUS      current
    DESCRIPTION
        "Vendor short name. Reconstructed from data returned by
         ISCOM2624G-4GE-PWR-AC, software 3.60.311 (ROS 5.2.1); Raisecom
         publishes no MIB for this object."
    ::= { raisecomDeviceInfo 17 }

raisecomDeviceManufacturer OBJECT-TYPE
    SYNTAX      DisplayString
    MAX-ACCESS  read-only
    STATUS      current
    DESCRIPTION
        "Manufacturer full name. Reconstructed from data returned by
         ISCOM2624G-4GE-PWR-AC, software 3.60.311 (ROS 5.2.1); Raisecom
         publishes no MIB for this object."
    ::= { raisecomDeviceInfo 18 }

raisecomDeviceModelName OBJECT-TYPE
    SYNTAX      DisplayString
    MAX-ACCESS  read-only
    STATUS      current
    DESCRIPTION
        "Model name, e.g. ISCOM2624G-4GE-PWR-AC. Reconstructed from data
         returned by ISCOM2624G-4GE-PWR-AC, software 3.60.311 (ROS
         5.2.1); Raisecom publishes no MIB for this object."
    ::= { raisecomDeviceInfo 19 }

raisecomDeviceMIBConformance OBJECT IDENTIFIER ::= { raisecomDeviceMIB 100 }
raisecomDeviceMIBGroups OBJECT IDENTIFIER ::= { raisecomDeviceMIBConformance 1 }
raisecomDeviceMIBCompliances OBJECT IDENTIFIER ::= { raisecomDeviceMIBConformance 2 }

raisecomDeviceMIBGroup OBJECT-GROUP
    OBJECTS {
        raisecomDeviceSoftwareVersion,
        raisecomDeviceHardwareVersion,
        raisecomDevicePortNumber,
        raisecomDeviceMacAddress,
        raisecomDeviceBootromVersion,
        raisecomDeviceSerialNumber,
        raisecomDeviceDescription,
        raisecomDeviceVendor,
        raisecomDeviceManufacturer,
        raisecomDeviceModelName
    }
    STATUS      current
    DESCRIPTION
        "Objects of RAISECOM-DEVICE-MIB."
    ::= { raisecomDeviceMIBGroups 1 }

raisecomDeviceMIBCompliance MODULE-COMPLIANCE
    STATUS      current
    DESCRIPTION
        "Devices implementing RAISECOM-DEVICE-MIB."
    MODULE
        MANDATORY-GROUPS { raisecomDeviceMIBGroup }
    ::= { raisecomDeviceMIBCompliances 1 }

END
