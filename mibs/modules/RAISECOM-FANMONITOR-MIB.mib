-- RAISECOM-FANMONITOR-MIB
--
-- Generated by mibs/gen_mibs.py; edit the generator, not this file.
-- Unofficial MIB for Raisecom ISCOM2600G switches, written from what
-- an ISCOM2624G-4GE-PWR-AC with software 3.60.311 (ROS 5.2.1) actually returns. Objects marked
-- "Reconstructed" have no published Raisecom MIB.
--

RAISECOM-FANMONITOR-MIB DEFINITIONS ::= BEGIN

IMPORTS
    MODULE-IDENTITY,
    OBJECT-TYPE,
    Unsigned32
        FROM SNMPv2-SMI
    MODULE-COMPLIANCE,
    OBJECT-GROUP
        FROM SNMPv2-CONF
    raisecomSystem
        FROM RAISECOM-SYSTEM-MIB;

raisecomFanMonitor MODULE-IDENTITY
    LAST-UPDATED "202610210000Z"
    ORGANIZATION "raisecom-snmp-exporter project (unofficial, not a Raisecom publication)"
    CONTACT-INFO
        "See README.md in the raisecom-snmp-exporter repository."
    DESCRIPTION
        "Fan monitoring of Raisecom ROS devices."
    REVISION     "202610210000Z"
    DESCRIPTION
        "Initial version."
    ::= { raisecomSystem 5 }

raisecomFanMonitorMibObjects OBJECT IDENTIFIER ::= { raisecomFanMonitor 2 }

raisecomFanMonitorGlobalGroup OBJECT IDENTIFIER ::= { raisecomFanMonitorMibObjects 1 }

raisecomFanMonitorMode OBJECT-TYPE
    SYNTAX      INTEGER { enforce(1), auto(2) }
    MAX-ACCESS  read-write
    STATUS      current
    DESCRIPTION
        "Fan control mode: enforce(1) uses a fixed speed level, auto(2)
         follows the temperature."
    ::= { raisecomFanMonitorGlobalGroup 1 }

raisecomFanMonitorSpdLevel OBJECT-TYPE
    SYNTAX      Unsigned32 (1..4)
    MAX-ACCESS  read-write
    STATUS      current
    DESCRIPTION
        "Speed level used in enforce mode."
    ::= { raisecomFanMonitorGlobalGroup 2 }

raisecomFanMonitorNumber OBJECT-TYPE
    SYNTAX      Unsigned32
    MAX-ACCESS  read-only
    STATUS      current
    DESCRIPTION
        "Number of monitored fans."
    ::= { raisecomFanMonitorGlobalGroup 3 }

raisecomFanMonitorLevlNumber OBJECT-TYPE
    SYNTAX      Unsigned32
    MAX-ACCESS  read-only
    STATUS      current
    DESCRIPTION
        "Number of fan speed levels."
    ::= { raisecomFanMonitorGlobalGroup 4 }

raisecomFanCardState OBJECT-TYPE
    SYNTAX      INTEGER { allDown(1), allUp(2), card1Up(3), card2Up(4) }
    MAX-ACCESS  read-only
    STATUS      current
    DESCRIPTION
        "State of the fan cards."
    ::= { raisecomFanMonitorGlobalGroup 5 }

raisecomFanCardSerialNumber OBJECT-TYPE
    SYNTAX      OCTET STRING (SIZE (0..64))
    MAX-ACCESS  read-only
    STATUS      current
    DESCRIPTION
        "Serial number of the fan card."
    ::= { raisecomFanMonitorGlobalGroup 6 }

raisecomFanMonitorTrapSendEnable OBJECT-TYPE
    SYNTAX      INTEGER { disable(0), enable(1) }
    MAX-ACCESS  read-write
    STATUS      current
    DESCRIPTION
        "Whether fan traps are sent."
    ::= { raisecomFanMonitorGlobalGroup 7 }

raisecomFanMonitorStateTable OBJECT-TYPE
    SYNTAX      SEQUENCE OF RaisecomFanMonitorStateEntry
    MAX-ACCESS  not-accessible
    STATUS      current
    DESCRIPTION
        "Fan state table."
    ::= { raisecomFanMonitorMibObjects 2 }

raisecomFanMonitorStateEntry OBJECT-TYPE
    SYNTAX      RaisecomFanMonitorStateEntry
    MAX-ACCESS  not-accessible
    STATUS      current
    DESCRIPTION
        "State of one fan."
    INDEX       { raisecomFanIndex }
    ::= { raisecomFanMonitorStateTable 1 }

RaisecomFanMonitorStateEntry ::= SEQUENCE {
    raisecomFanIndex              Unsigned32,
    raisecomFanSpeedValue         Unsigned32,
    raisecomFanWorkState          INTEGER,
    raisecomFanSpeedCurrentLevel  Unsigned32
}

raisecomFanIndex OBJECT-TYPE
    SYNTAX      Unsigned32 (1..64)
    MAX-ACCESS  not-accessible
    STATUS      current
    DESCRIPTION
        "Fan number."
    ::= { raisecomFanMonitorStateEntry 1 }

raisecomFanSpeedValue OBJECT-TYPE
    SYNTAX      Unsigned32
    UNITS       "rpm"
    MAX-ACCESS  read-only
    STATUS      current
    DESCRIPTION
        "Current fan speed."
    ::= { raisecomFanMonitorStateEntry 2 }

raisecomFanWorkState OBJECT-TYPE
    SYNTAX      INTEGER { normal(1), abnormal(2) }
    MAX-ACCESS  read-only
    STATUS      current
    DESCRIPTION
        "Current fan state."
    ::= { raisecomFanMonitorStateEntry 3 }

raisecomFanSpeedCurrentLevel OBJECT-TYPE
    SYNTAX      Unsigned32 (1..4)
    MAX-ACCESS  read-only
    STATUS      current
    DESCRIPTION
        "Speed level currently selected by temperature."
    ::= { raisecomFanMonitorStateEntry 4 }

raisecomFanMonitorConformance OBJECT IDENTIFIER ::= { raisecomFanMonitor 100 }
raisecomFanMonitorGroups OBJECT IDENTIFIER ::= { raisecomFanMonitorConformance 1 }
raisecomFanMonitorCompliances OBJECT IDENTIFIER ::= { raisecomFanMonitorConformance 2 }

raisecomFanMonitorGroup OBJECT-GROUP
    OBJECTS {
        raisecomFanMonitorMode,
        raisecomFanMonitorSpdLevel,
        raisecomFanMonitorNumber,
        raisecomFanMonitorLevlNumber,
        raisecomFanCardState,
        raisecomFanCardSerialNumber,
        raisecomFanMonitorTrapSendEnable,
        raisecomFanSpeedValue,
        raisecomFanWorkState,
        raisecomFanSpeedCurrentLevel
    }
    STATUS      current
    DESCRIPTION
        "Objects of RAISECOM-FANMONITOR-MIB."
    ::= { raisecomFanMonitorGroups 1 }

raisecomFanMonitorCompliance MODULE-COMPLIANCE
    STATUS      current
    DESCRIPTION
        "Devices implementing RAISECOM-FANMONITOR-MIB."
    MODULE
        MANDATORY-GROUPS { raisecomFanMonitorGroup }
    ::= { raisecomFanMonitorCompliances 1 }

END
