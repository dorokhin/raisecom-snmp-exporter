-- RAISECOM-POE-MIB
--
-- Generated by mibs/gen_mibs.py; edit the generator, not this file.
-- Unofficial MIB for Raisecom ISCOM2600G switches, written from what
-- an ISCOM2624G-4GE-PWR-AC with software 3.60.311 (ROS 5.2.1) actually returns. Objects marked
-- "Reconstructed" have no published Raisecom MIB.
--

RAISECOM-POE-MIB DEFINITIONS ::= BEGIN

IMPORTS
    Gauge32,
    Integer32,
    MODULE-IDENTITY,
    OBJECT-TYPE
        FROM SNMPv2-SMI
    MODULE-COMPLIANCE,
    OBJECT-GROUP
        FROM SNMPv2-CONF
    ifIndex
        FROM IF-MIB
    EnableVar,
    iscomSwitch
        FROM RAISECOM-BASE-MIB;

raisecomPoeMIB MODULE-IDENTITY
    LAST-UPDATED "202610210000Z"
    ORGANIZATION "raisecom-snmp-exporter project (unofficial, not a Raisecom publication)"
    CONTACT-INFO
        "See README.md in the raisecom-snmp-exporter repository."
    DESCRIPTION
        "Power over Ethernet measurements of ISCOM PoE switches,
         complementing POWER-ETHERNET-MIB (RFC 3621) with per-port power,
         voltage and current. Reconstructed from data returned by
         ISCOM2624G-4GE-PWR-AC, software 3.60.311 (ROS 5.2.1); Raisecom
         publishes no MIB for this object."
    REVISION     "202610210000Z"
    DESCRIPTION
        "Initial version."
    ::= { iscomSwitch 51 }

raisecomPoePortTable OBJECT-TYPE
    SYNTAX      SEQUENCE OF RaisecomPoePortEntry
    MAX-ACCESS  not-accessible
    STATUS      current
    DESCRIPTION
        "Per-port PoE measurements."
    ::= { raisecomPoeMIB 1 }

raisecomPoePortEntry OBJECT-TYPE
    SYNTAX      RaisecomPoePortEntry
    MAX-ACCESS  not-accessible
    STATUS      current
    DESCRIPTION
        "PoE measurements of one port, indexed like pethPsePortTable (PSE
         group, port ifIndex)."
    INDEX       { raisecomPoePortGroupIndex, ifIndex }
    ::= { raisecomPoePortTable 1 }

RaisecomPoePortEntry ::= SEQUENCE {
    raisecomPoePortPeakPower        Gauge32,
    raisecomPoePortPower            Gauge32,
    raisecomPoePortPowerInstant     Gauge32,
    raisecomPoePortVoltage          Gauge32,
    raisecomPoePortCurrent          Gauge32,
    raisecomPoePortPowerLimit       Gauge32,
    raisecomPoePortAdminStatus      EnableVar,
    raisecomPoePortForcePower       EnableVar,
    raisecomPoePortScheduleProfile  Integer32,
    raisecomPoePortAliveCheck       EnableVar,
    raisecomPoePortAliveAction      INTEGER,
    raisecomPoePortRebootInterval   Integer32,
    raisecomPoePortLinktraceTrack   Integer32,
    raisecomPoePortOperStatus       EnableVar,
    raisecomPoePortGroupIndex       Integer32
}

raisecomPoePortGroupIndex OBJECT-TYPE
    SYNTAX      Integer32 (1..2147483647)
    MAX-ACCESS  not-accessible
    STATUS      current
    DESCRIPTION
        "PSE group, always 1 on single-PSE switches. Matches
         pethPsePortGroupIndex."
    ::= { raisecomPoePortEntry 100 }

raisecomPoePortPeakPower OBJECT-TYPE
    SYNTAX      Gauge32
    UNITS       "milliwatts"
    MAX-ACCESS  read-only
    STATUS      current
    DESCRIPTION
        "Highest power drawn on the port. Reconstructed from data
         returned by ISCOM2624G-4GE-PWR-AC, software 3.60.311 (ROS
         5.2.1); Raisecom publishes no MIB for this object."
    ::= { raisecomPoePortEntry 1 }

raisecomPoePortPower OBJECT-TYPE
    SYNTAX      Gauge32
    UNITS       "milliwatts"
    MAX-ACCESS  read-only
    STATUS      current
    DESCRIPTION
        "Power drawn by the powered device, smoothed (moving average of
         raisecomPoePortPowerInstant). Reconstructed from data returned
         by ISCOM2624G-4GE-PWR-AC, software 3.60.311 (ROS 5.2.1);
         Raisecom publishes no MIB for this object."
    ::= { raisecomPoePortEntry 2 }

raisecomPoePortPowerInstant OBJECT-TYPE
    SYNTAX      Gauge32
    UNITS       "milliwatts"
    MAX-ACCESS  read-only
    STATUS      current
    DESCRIPTION
        "Latest power sample, 100 mW resolution; this is the 'Output
         Power(mW)' column of CLI 'show poe interface'. Reconstructed
         from data returned by ISCOM2624G-4GE-PWR-AC, software 3.60.311
         (ROS 5.2.1); Raisecom publishes no MIB for this object."
    ::= { raisecomPoePortEntry 3 }

raisecomPoePortVoltage OBJECT-TYPE
    SYNTAX      Gauge32
    UNITS       "millivolts"
    MAX-ACCESS  read-only
    STATUS      current
    DESCRIPTION
        "Output voltage ('Output Voltage(mV)' in CLI). Reconstructed from
         data returned by ISCOM2624G-4GE-PWR-AC, software 3.60.311 (ROS
         5.2.1); Raisecom publishes no MIB for this object."
    ::= { raisecomPoePortEntry 4 }

raisecomPoePortCurrent OBJECT-TYPE
    SYNTAX      Gauge32
    UNITS       "milliamperes"
    MAX-ACCESS  read-only
    STATUS      current
    DESCRIPTION
        "Output current ('Output Current(mA)' in CLI). Reconstructed from
         data returned by ISCOM2624G-4GE-PWR-AC, software 3.60.311 (ROS
         5.2.1); Raisecom publishes no MIB for this object."
    ::= { raisecomPoePortEntry 5 }

raisecomPoePortPowerLimit OBJECT-TYPE
    SYNTAX      Gauge32
    UNITS       "milliwatts"
    MAX-ACCESS  read-only
    STATUS      current
    DESCRIPTION
        "Maximum power the port may deliver ('Max Power(mW)' in CLI, set
         with 'poe max-power'). Reconstructed from data returned by
         ISCOM2624G-4GE-PWR-AC, software 3.60.311 (ROS 5.2.1); Raisecom
         publishes no MIB for this object."
    ::= { raisecomPoePortEntry 6 }

raisecomPoePortAdminStatus OBJECT-TYPE
    SYNTAX      EnableVar
    MAX-ACCESS  read-only
    STATUS      current
    DESCRIPTION
        "Administrative PoE state of the port (CLI 'poe enable|disable',
         shown as 'POE administrator status'). 'poe disable' changes this
         column together with raisecomPoePortOperStatus and
         pethPsePortAdminEnable; it is taken as the administrative one
         because columns 7..14 all hold port settings. Reconstructed from
         data returned by ISCOM2624G-4GE-PWR-AC, software 3.60.311 (ROS
         5.2.1); Raisecom publishes no MIB for this object."
    ::= { raisecomPoePortEntry 7 }

raisecomPoePortForcePower OBJECT-TYPE
    SYNTAX      EnableVar
    MAX-ACCESS  read-only
    STATUS      current
    DESCRIPTION
        "Force power without PD detection (CLI 'poe force-power', shown
         as 'POE force-power status'). Reconstructed from data returned
         by ISCOM2624G-4GE-PWR-AC, software 3.60.311 (ROS 5.2.1);
         Raisecom publishes no MIB for this object."
    ::= { raisecomPoePortEntry 8 }

raisecomPoePortScheduleProfile OBJECT-TYPE
    SYNTAX      Integer32 (0..2147483647)
    MAX-ACCESS  read-only
    STATUS      current
    DESCRIPTION
        "PoE schedule profile bound to the port, 0 for none (CLI 'poe
         schedule profile', shown as 'POE schedule profile'). Inferred
         from the column position and the CLI field order; not verified.
         Reconstructed from data returned by ISCOM2624G-4GE-PWR-AC,
         software 3.60.311 (ROS 5.2.1); Raisecom publishes no MIB for
         this object."
    ::= { raisecomPoePortEntry 9 }

raisecomPoePortAliveCheck OBJECT-TYPE
    SYNTAX      EnableVar
    MAX-ACCESS  read-only
    STATUS      current
    DESCRIPTION
        "PD alive check (CLI 'poe alive check enable|disable', shown as
         'POE PD check status'). Mapping verified by changing the setting
         via CLI and observing this column. Reconstructed from data
         returned by ISCOM2624G-4GE-PWR-AC, software 3.60.311 (ROS
         5.2.1); Raisecom publishes no MIB for this object."
    ::= { raisecomPoePortEntry 10 }

raisecomPoePortAliveAction OBJECT-TYPE
    SYNTAX      INTEGER { none(0), reboot(1), rebootAlarm(2), alarm(3) }
    MAX-ACCESS  read-only
    STATUS      current
    DESCRIPTION
        "Action when the PD alive check fails (CLI 'poe alive action
         reboot|reboot-alarm|alarm', 'no poe alive action' gives none;
         shown as 'POE PD fail action', N/A for none). Mapping verified
         by changing the setting via CLI and observing this column.
         Reconstructed from data returned by ISCOM2624G-4GE-PWR-AC,
         software 3.60.311 (ROS 5.2.1); Raisecom publishes no MIB for
         this object."
    ::= { raisecomPoePortEntry 11 }

raisecomPoePortRebootInterval OBJECT-TYPE
    SYNTAX      Integer32 (0..2147483647)
    UNITS       "seconds"
    MAX-ACCESS  read-only
    STATUS      current
    DESCRIPTION
        "Power-off time when rebooting a failed PD (CLI 'poe reboot
         interval', shown as 'POE PD fail reboot interval'). Mapping
         verified by changing the setting via CLI and observing this
         column. Reconstructed from data returned by ISCOM2624G-4GE-PWR-
         AC, software 3.60.311 (ROS 5.2.1); Raisecom publishes no MIB for
         this object."
    ::= { raisecomPoePortEntry 12 }

raisecomPoePortLinktraceTrack OBJECT-TYPE
    SYNTAX      Integer32 (0..128)
    MAX-ACCESS  read-only
    STATUS      current
    DESCRIPTION
        "Track object the port follows, 0 for none (CLI 'poe linktrace
         track <1-128>', 'no poe linktrace' gives 0; shown as 'POE PD
         linktrace'). Mapping verified by changing the setting via CLI
         and observing this column. Reconstructed from data returned by
         ISCOM2624G-4GE-PWR-AC, software 3.60.311 (ROS 5.2.1); Raisecom
         publishes no MIB for this object."
    ::= { raisecomPoePortEntry 14 }

raisecomPoePortOperStatus OBJECT-TYPE
    SYNTAX      EnableVar
    MAX-ACCESS  read-only
    STATUS      current
    DESCRIPTION
        "Operational PoE state of the port (shown as 'POE operation
         status' / 'POE actual running status'; the two could not be told
         apart). Follows raisecomPoePortAdminStatus when PoE is disabled
         on the port. Reconstructed from data returned by ISCOM2624G-4GE-
         PWR-AC, software 3.60.311 (ROS 5.2.1); Raisecom publishes no MIB
         for this object."
    ::= { raisecomPoePortEntry 15 }

raisecomPoePseTable OBJECT-TYPE
    SYNTAX      SEQUENCE OF RaisecomPoePseEntry
    MAX-ACCESS  not-accessible
    STATUS      current
    DESCRIPTION
        "Per-PSE PoE totals."
    ::= { raisecomPoeMIB 2 }

raisecomPoePseEntry OBJECT-TYPE
    SYNTAX      RaisecomPoePseEntry
    MAX-ACCESS  not-accessible
    STATUS      current
    DESCRIPTION
        "Totals of one PSE."
    INDEX       { raisecomPoePseGroupIndex }
    ::= { raisecomPoePseTable 1 }

RaisecomPoePseEntry ::= SEQUENCE {
    raisecomPoePseAveragePower           Gauge32,
    raisecomPoePsePeakPower              Gauge32,
    raisecomPoePseLegacyDetection        EnableVar,
    raisecomPoePseTemperatureProtection  EnableVar,
    raisecomPoePsePower                  Gauge32,
    raisecomPoePseGroupIndex             Integer32
}

raisecomPoePseGroupIndex OBJECT-TYPE
    SYNTAX      Integer32 (1..2147483647)
    MAX-ACCESS  not-accessible
    STATUS      current
    DESCRIPTION
        "PSE group, always 1 on single-PSE switches. Matches
         pethMainPseGroupIndex."
    ::= { raisecomPoePseEntry 100 }

raisecomPoePseAveragePower OBJECT-TYPE
    SYNTAX      Gauge32
    UNITS       "milliwatts"
    MAX-ACCESS  read-only
    STATUS      current
    DESCRIPTION
        "Total power delivered, averaged by the switch ('Average
         Power(mW)' in CLI 'show poe pse'). The instantaneous total in
         whole watts is pethMainPseConsumptionPower ('Output Power(W)').
         Reconstructed from data returned by ISCOM2624G-4GE-PWR-AC,
         software 3.60.311 (ROS 5.2.1); Raisecom publishes no MIB for
         this object."
    ::= { raisecomPoePseEntry 1 }

raisecomPoePsePeakPower OBJECT-TYPE
    SYNTAX      Gauge32
    UNITS       "milliwatts"
    MAX-ACCESS  read-only
    STATUS      current
    DESCRIPTION
        "Highest total power delivered ('Peak Power(mW)' in CLI).
         Reconstructed from data returned by ISCOM2624G-4GE-PWR-AC,
         software 3.60.311 (ROS 5.2.1); Raisecom publishes no MIB for
         this object."
    ::= { raisecomPoePseEntry 2 }

raisecomPoePsePower OBJECT-TYPE
    SYNTAX      Gauge32
    UNITS       "watts"
    MAX-ACCESS  read-only
    STATUS      current
    DESCRIPTION
        "Power budget of the PSE ('Wattage Rating(W)' in CLI,
         pethMainPsePower). Reconstructed from data returned by
         ISCOM2624G-4GE-PWR-AC, software 3.60.311 (ROS 5.2.1); Raisecom
         publishes no MIB for this object."
    ::= { raisecomPoePseEntry 8 }

raisecomPoePseLegacyDetection OBJECT-TYPE
    SYNTAX      EnableVar
    MAX-ACCESS  read-only
    STATUS      current
    DESCRIPTION
        "Detection of legacy (pre-802.3af) powered devices (CLI 'poe
         legacy enable|disable', shown as 'PSE legacy detection').
         Mapping verified by changing the setting via CLI and observing
         this column. Reconstructed from data returned by ISCOM2624G-4GE-
         PWR-AC, software 3.60.311 (ROS 5.2.1); Raisecom publishes no MIB
         for this object."
    ::= { raisecomPoePseEntry 3 }

raisecomPoePseTemperatureProtection OBJECT-TYPE
    SYNTAX      EnableVar
    MAX-ACCESS  read-only
    STATUS      current
    DESCRIPTION
        "Over-temperature protection of the PSE (CLI 'poe temperature-
         protection enable|disable', shown as 'Switch temperature-
         protection'). Mapping verified by changing the setting via CLI
         and observing this column. Reconstructed from data returned by
         ISCOM2624G-4GE-PWR-AC, software 3.60.311 (ROS 5.2.1); Raisecom
         publishes no MIB for this object."
    ::= { raisecomPoePseEntry 5 }

raisecomPoeMIBConformance OBJECT IDENTIFIER ::= { raisecomPoeMIB 100 }
raisecomPoeMIBGroups OBJECT IDENTIFIER ::= { raisecomPoeMIBConformance 1 }
raisecomPoeMIBCompliances OBJECT IDENTIFIER ::= { raisecomPoeMIBConformance 2 }

raisecomPoeMIBGroup OBJECT-GROUP
    OBJECTS {
        raisecomPoePortPeakPower,
        raisecomPoePortPower,
        raisecomPoePortPowerInstant,
        raisecomPoePortVoltage,
        raisecomPoePortCurrent,
        raisecomPoePortPowerLimit,
        raisecomPoePortAdminStatus,
        raisecomPoePortForcePower,
        raisecomPoePortScheduleProfile,
        raisecomPoePortAliveCheck,
        raisecomPoePortAliveAction,
        raisecomPoePortRebootInterval,
        raisecomPoePortLinktraceTrack,
        raisecomPoePortOperStatus,
        raisecomPoePseAveragePower,
        raisecomPoePsePeakPower,
        raisecomPoePsePower,
        raisecomPoePseLegacyDetection,
        raisecomPoePseTemperatureProtection
    }
    STATUS      current
    DESCRIPTION
        "Objects of RAISECOM-POE-MIB."
    ::= { raisecomPoeMIBGroups 1 }

raisecomPoeMIBCompliance MODULE-COMPLIANCE
    STATUS      current
    DESCRIPTION
        "Devices implementing RAISECOM-POE-MIB."
    MODULE
        MANDATORY-GROUPS { raisecomPoeMIBGroup }
    ::= { raisecomPoeMIBCompliances 1 }

END
