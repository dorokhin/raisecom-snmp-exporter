-- RAISECOM-BASE-MIB
--
-- Generated by mibs/gen_mibs.py; edit the generator, not this file.
-- Unofficial MIB for Raisecom ISCOM2600G switches, written from what
-- an ISCOM2624G-4GE-PWR-AC with software 3.60.311 (ROS 5.2.1) actually returns. Objects marked
-- "Reconstructed" have no published Raisecom MIB.
--

RAISECOM-BASE-MIB DEFINITIONS ::= BEGIN

IMPORTS
    MODULE-IDENTITY,
    enterprises
        FROM SNMPv2-SMI
    TEXTUAL-CONVENTION
        FROM SNMPv2-TC;

raisecom MODULE-IDENTITY
    LAST-UPDATED "202610210000Z"
    ORGANIZATION "raisecom-snmp-exporter project (unofficial, not a Raisecom publication)"
    CONTACT-INFO
        "See README.md in the raisecom-snmp-exporter repository."
    DESCRIPTION
        "Root of the Raisecom enterprise tree and textual conventions
         shared by the other modules."
    REVISION     "202610210000Z"
    DESCRIPTION
        "Initial version."
    ::= { enterprises 8886 }

EnableVar ::= TEXTUAL-CONVENTION
    STATUS      current
    DESCRIPTION
        "Enable or disable a function."
    SYNTAX      INTEGER { enable(1), disable(2) }

raisecomAgent OBJECT IDENTIFIER ::= { raisecom 1 }

iscomSeries OBJECT IDENTIFIER ::= { raisecom 6 }

iscomSwitch OBJECT IDENTIFIER ::= { iscomSeries 1 }

END
