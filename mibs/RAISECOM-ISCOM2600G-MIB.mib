-- RAISECOM-ISCOM2600G-MIB
--
-- Generated by mibs/gen_mibs.py; edit the generator, not this file.
-- Unofficial MIB for Raisecom ISCOM2600G switches, written from what
-- an ISCOM2624G-4GE-PWR-AC with software 3.60.311 (ROS 5.2.1) actually returns. Objects marked
-- "Reconstructed" have no published Raisecom MIB.
--

RAISECOM-ISCOM2600G-MIB DEFINITIONS ::= BEGIN

IMPORTS
    Gauge32,
    Integer32,
    MODULE-IDENTITY,
    OBJECT-TYPE,
    TimeTicks,
    Unsigned32,
    enterprises
        FROM SNMPv2-SMI
    DisplayString,
    MacAddress,
    TEXTUAL-CONVENTION
        FROM SNMPv2-TC;

raisecom MODULE-IDENTITY
    LAST-UPDATED "202610210000Z"
    ORGANIZATION "raisecom-snmp-exporter project (unofficial, not a Raisecom publication)"
    CONTACT-INFO
        "See README.md in the raisecom-snmp-exporter repository."
    DESCRIPTION
        "Self-contained MIB with every private object the
         raisecom_exporter reads from Raisecom ISCOM2600G switches:
         device identification, port descriptions, PoE measurements, CPU,
         memory, temperature, fans and optical transceivers with DDM. It
         imports only SNMPv2-SMI, SNMPv2-TC and SNMPv2-CONF. The same
         objects are available split into conventional modules in
         mibs/modules."
    REVISION     "202610210000Z"
    DESCRIPTION
        "Initial version."
    ::= { enterprises 8886 }

EnableVar ::= TEXTUAL-CONVENTION
    STATUS      current
    DESCRIPTION
        "Enable or disable a function."
    SYNTAX      INTEGER { enable(1), disable(2) }

OpticalParameterType ::= TEXTUAL-CONVENTION
    STATUS      current
    DESCRIPTION
        "Monitored DDM parameter. The published Raisecom MIB names value
         5 laserTemperature; software 3.60.311 (ROS 5.2.1) returns the
         3.3 V supply voltage there (about 3300 mV with 2900..3600 mV
         thresholds)."
    SYNTAX      INTEGER { transceiverTemperature(1), txBiasCurrent(2), txPower(3), rxPower(4), supplyVoltage(5) }

OpticalParameterValue ::= TEXTUAL-CONVENTION
    DISPLAY-HINT "d-3"
    STATUS      current
    DESCRIPTION
        "DDM value in thousandths of the base unit:
         transceiverTemperature in millidegrees Celsius, txBiasCurrent in
         microamperes, txPower and rxPower in thousandths of dBm,
         supplyVoltage in millivolts. -1000000 means not available."
    SYNTAX      Integer32 (-1000000 | -40000..6553600)

raisecomAgent OBJECT IDENTIFIER ::= { raisecom 1 }

iscomSeries OBJECT IDENTIFIER ::= { raisecom 6 }

iscomSwitch OBJECT IDENTIFIER ::= { iscomSeries 1 }

-- Objects of RAISECOM-SYSTEM-MIB

raisecomSystem OBJECT IDENTIFIER ::= { raisecomAgent 1 }

raisecomCpu OBJECT IDENTIFIER ::= { raisecomSystem 1 }

raisecomCPUTableGroup OBJECT IDENTIFIER ::= { raisecomCpu 5 }

raisecomCPUUtilizationGroup OBJECT IDENTIFIER ::= { raisecomCPUTableGroup 1 }

raisecomTotalCPUUtilizationTable OBJECT-TYPE
    SYNTAX      SEQUENCE OF RaisecomTotalCPUUtilizationEntry
    MAX-ACCESS  not-accessible
    STATUS      current
    DESCRIPTION
        "Total CPU utilization per averaging period. Position verified on
         software 3.60.311 (ROS 5.2.1), where it differs from the
         published Raisecom MIB."
    ::= { raisecomCPUUtilizationGroup 4 }

raisecomTotalCPUUtilizationEntry OBJECT-TYPE
    SYNTAX      RaisecomTotalCPUUtilizationEntry
    MAX-ACCESS  not-accessible
    STATUS      current
    DESCRIPTION
        "CPU utilization for one period."
    INDEX       { raisecomTotalCPUPeriod }
    ::= { raisecomTotalCPUUtilizationTable 1 }

RaisecomTotalCPUUtilizationEntry ::= SEQUENCE {
    raisecomTotalCPUPeriod       INTEGER,
    raisecomTotalCPUUtilization  Integer32
}

raisecomTotalCPUPeriod OBJECT-TYPE
    SYNTAX      INTEGER { oneSec(1), fiveSec(2), oneMin(3), tenMin(4), twoHour(5) }
    MAX-ACCESS  not-accessible
    STATUS      current
    DESCRIPTION
        "Period over which CPU utilization is averaged."
    ::= { raisecomTotalCPUUtilizationEntry 1 }

raisecomTotalCPUUtilization OBJECT-TYPE
    SYNTAX      Integer32 (0..100)
    UNITS       "percent"
    MAX-ACCESS  read-only
    STATUS      current
    DESCRIPTION
        "CPU busy percentage over the period."
    ::= { raisecomTotalCPUUtilizationEntry 2 }

raisecomMemory OBJECT IDENTIFIER ::= { raisecomSystem 3 }

raisecomMemoryTotal OBJECT-TYPE
    SYNTAX      Integer32
    UNITS       "bytes"
    MAX-ACCESS  read-only
    STATUS      current
    DESCRIPTION
        "Total memory of the system. Position verified on software
         3.60.311 (ROS 5.2.1), where it differs from the published
         Raisecom MIB."
    ::= { raisecomMemory 1 }

raisecomMemoryAvailable OBJECT-TYPE
    SYNTAX      Integer32
    UNITS       "bytes"
    MAX-ACCESS  read-only
    STATUS      current
    DESCRIPTION
        "Available memory of the system."
    ::= { raisecomMemory 2 }

raisecomMemoryUtil OBJECT-TYPE
    SYNTAX      Integer32 (0..100)
    UNITS       "percent"
    MAX-ACCESS  read-only
    STATUS      current
    DESCRIPTION
        "Current memory utilization. The published MIB types this OCTET
         STRING; software 3.60.311 (ROS 5.2.1) returns INTEGER."
    ::= { raisecomMemory 3 }

raisecomMemoryTrapEnable OBJECT-TYPE
    SYNTAX      EnableVar
    MAX-ACCESS  read-write
    STATUS      current
    DESCRIPTION
        "Whether the memory trap is enabled."
    ::= { raisecomMemory 4 }

raisecomMemoryThrshd OBJECT-TYPE
    SYNTAX      Integer32 (0..100)
    UNITS       "percent"
    MAX-ACCESS  read-write
    STATUS      current
    DESCRIPTION
        "Memory utilization alarm threshold."
    ::= { raisecomMemory 5 }

raisecomMemoryThrshdRecover OBJECT-TYPE
    SYNTAX      Integer32 (0..100)
    UNITS       "percent"
    MAX-ACCESS  read-write
    STATUS      current
    DESCRIPTION
        "Memory utilization at which the alarm clears."
    ::= { raisecomMemory 6 }

raisecomMemoryMonInterval OBJECT-TYPE
    SYNTAX      Integer32
    UNITS       "seconds"
    MAX-ACCESS  read-write
    STATUS      current
    DESCRIPTION
        "Memory monitor interval."
    ::= { raisecomMemory 7 }

raisecomInformation OBJECT IDENTIFIER ::= { raisecomSystem 4 }

raisecomTemperature OBJECT IDENTIFIER ::= { raisecomInformation 2 }

raisecomTemperatureValue OBJECT-TYPE
    SYNTAX      Integer32
    UNITS       "degrees Celsius"
    MAX-ACCESS  read-only
    STATUS      current
    DESCRIPTION
        "Current board temperature."
    ::= { raisecomTemperature 1 }

raisecomTemperatureMin OBJECT-TYPE
    SYNTAX      Integer32
    UNITS       "degrees Celsius"
    MAX-ACCESS  read-only
    STATUS      current
    DESCRIPTION
        "Lowest temperature since boot."
    ::= { raisecomTemperature 2 }

raisecomTemperatureMax OBJECT-TYPE
    SYNTAX      Integer32
    UNITS       "degrees Celsius"
    MAX-ACCESS  read-only
    STATUS      current
    DESCRIPTION
        "Highest temperature since boot."
    ::= { raisecomTemperature 3 }

raisecomTemperatureTrapEnable OBJECT-TYPE
    SYNTAX      EnableVar
    MAX-ACCESS  read-write
    STATUS      current
    DESCRIPTION
        "Whether the temperature trap is enabled."
    ::= { raisecomTemperature 4 }

raisecomTemperatureThresholdLow OBJECT-TYPE
    SYNTAX      Integer32
    UNITS       "degrees Celsius"
    MAX-ACCESS  read-write
    STATUS      current
    DESCRIPTION
        "Low temperature alarm threshold."
    ::= { raisecomTemperature 5 }

raisecomTemperatureThresholdHigh OBJECT-TYPE
    SYNTAX      Integer32
    UNITS       "degrees Celsius"
    MAX-ACCESS  read-write
    STATUS      current
    DESCRIPTION
        "High temperature alarm threshold."
    ::= { raisecomTemperature 6 }

raisecomTemperatureTrapTimes OBJECT-TYPE
    SYNTAX      Integer32
    MAX-ACCESS  read-only
    STATUS      current
    DESCRIPTION
        "Number of abnormal temperature events."
    ::= { raisecomTemperature 7 }

raisecomTemperatureHighTimes OBJECT-TYPE
    SYNTAX      Integer32
    MAX-ACCESS  read-only
    STATUS      current
    DESCRIPTION
        "Number of high temperature events."
    ::= { raisecomTemperature 8 }

raisecomTemperatureLowTimes OBJECT-TYPE
    SYNTAX      Integer32
    MAX-ACCESS  read-only
    STATUS      current
    DESCRIPTION
        "Number of low temperature events."
    ::= { raisecomTemperature 9 }

-- Objects of RAISECOM-FANMONITOR-MIB

raisecomFanMonitor OBJECT IDENTIFIER ::= { raisecomSystem 5 }

raisecomFanMonitorMibObjects OBJECT IDENTIFIER ::= { raisecomFanMonitor 2 }

raisecomFanMonitorGlobalGroup OBJECT IDENTIFIER ::= { raisecomFanMonitorMibObjects 1 }

raisecomFanMonitorMode OBJECT-TYPE
    SYNTAX      INTEGER { enforce(1), auto(2) }
    MAX-ACCESS  read-write
    STATUS      current
    DESCRIPTION
        "Fan control mode: enforce(1) uses a fixed speed level, auto(2)
         follows the temperature."
    ::= { raisecomFanMonitorGlobalGroup 1 }

raisecomFanMonitorSpdLevel OBJECT-TYPE
    SYNTAX      Unsigned32 (1..4)
    MAX-ACCESS  read-write
    STATUS      current
    DESCRIPTION
        "Speed level used in enforce mode."
    ::= { raisecomFanMonitorGlobalGroup 2 }

raisecomFanMonitorNumber OBJECT-TYPE
    SYNTAX      Unsigned32
    MAX-ACCESS  read-only
    STATUS      current
    DESCRIPTION
        "Number of monitored fans."
    ::= { raisecomFanMonitorGlobalGroup 3 }

raisecomFanMonitorLevlNumber OBJECT-TYPE
    SYNTAX      Unsigned32
    MAX-ACCESS  read-only
    STATUS      current
    DESCRIPTION
        "Number of fan speed levels."
    ::= { raisecomFanMonitorGlobalGroup 4 }

raisecomFanCardState OBJECT-TYPE
    SYNTAX      INTEGER { allDown(1), allUp(2), card1Up(3), card2Up(4) }
    MAX-ACCESS  read-only
    STATUS      current
    DESCRIPTION
        "State of the fan cards."
    ::= { raisecomFanMonitorGlobalGroup 5 }

raisecomFanCardSerialNumber OBJECT-TYPE
    SYNTAX      OCTET STRING (SIZE (0..64))
    MAX-ACCESS  read-only
    STATUS      current
    DESCRIPTION
        "Serial number of the fan card."
    ::= { raisecomFanMonitorGlobalGroup 6 }

raisecomFanMonitorTrapSendEnable OBJECT-TYPE
    SYNTAX      INTEGER { disable(0), enable(1) }
    MAX-ACCESS  read-write
    STATUS      current
    DESCRIPTION
        "Whether fan traps are sent."
    ::= { raisecomFanMonitorGlobalGroup 7 }

raisecomFanMonitorStateTable OBJECT-TYPE
    SYNTAX      SEQUENCE OF RaisecomFanMonitorStateEntry
    MAX-ACCESS  not-accessible
    STATUS      current
    DESCRIPTION
        "Fan state table."
    ::= { raisecomFanMonitorMibObjects 2 }

raisecomFanMonitorStateEntry OBJECT-TYPE
    SYNTAX      RaisecomFanMonitorStateEntry
    MAX-ACCESS  not-accessible
    STATUS      current
    DESCRIPTION
        "State of one fan."
    INDEX       { raisecomFanIndex }
    ::= { raisecomFanMonitorStateTable 1 }

RaisecomFanMonitorStateEntry ::= SEQUENCE {
    raisecomFanIndex              Unsigned32,
    raisecomFanSpeedValue         Unsigned32,
    raisecomFanWorkState          INTEGER,
    raisecomFanSpeedCurrentLevel  Unsigned32
}

raisecomFanIndex OBJECT-TYPE
    SYNTAX      Unsigned32 (1..64)
    MAX-ACCESS  not-accessible
    STATUS      current
    DESCRIPTION
        "Fan number."
    ::= { raisecomFanMonitorStateEntry 1 }

raisecomFanSpeedValue OBJECT-TYPE
    SYNTAX      Unsigned32
    UNITS       "rpm"
    MAX-ACCESS  read-only
    STATUS      current
    DESCRIPTION
        "Current fan speed."
    ::= { raisecomFanMonitorStateEntry 2 }

raisecomFanWorkState OBJECT-TYPE
    SYNTAX      INTEGER { normal(1), abnormal(2) }
    MAX-ACCESS  read-only
    STATUS      current
    DESCRIPTION
        "Current fan state."
    ::= { raisecomFanMonitorStateEntry 3 }

raisecomFanSpeedCurrentLevel OBJECT-TYPE
    SYNTAX      Unsigned32 (1..4)
    MAX-ACCESS  read-only
    STATUS      current
    DESCRIPTION
        "Speed level currently selected by temperature."
    ::= { raisecomFanMonitorStateEntry 4 }

-- Objects of RAISECOM-OPTICAL-TRANSCEIVER-MIB

raisecomOpticalTransceiver OBJECT IDENTIFIER ::= { raisecomAgent 18 }

raisecomOpticalTransceiverGlobalEnable OBJECT IDENTIFIER ::= { raisecomOpticalTransceiver 1 }

raisecomOpticalTransceiverNotifyEnable OBJECT-TYPE
    SYNTAX      EnableVar
    MAX-ACCESS  read-write
    STATUS      current
    DESCRIPTION
        "Whether transceiver notifications are sent."
    ::= { raisecomOpticalTransceiverGlobalEnable 1 }

raisecomOpticalTransceiverDDMEnable OBJECT-TYPE
    SYNTAX      EnableVar
    MAX-ACCESS  read-write
    STATUS      current
    DESCRIPTION
        "Whether digital diagnostics monitoring is enabled. DDM values
         are only populated when enabled."
    ::= { raisecomOpticalTransceiverGlobalEnable 2 }

raisecomOpticalTransceiverCheckPwdEnable OBJECT-TYPE
    SYNTAX      EnableVar
    MAX-ACCESS  read-write
    STATUS      current
    DESCRIPTION
        "Whether transceiver password checking is enabled."
    ::= { raisecomOpticalTransceiverGlobalEnable 3 }

raisecomOpticalTransceiverPollInterval OBJECT-TYPE
    SYNTAX      Integer32
    UNITS       "seconds"
    MAX-ACCESS  read-write
    STATUS      current
    DESCRIPTION
        "DDM poll interval."
    ::= { raisecomOpticalTransceiverGlobalEnable 4 }

raisecomOpticalTransceiverObjects OBJECT IDENTIFIER ::= { raisecomOpticalTransceiver 2 }

raisecomOpticalTransceiverInfoGroup OBJECT IDENTIFIER ::= { raisecomOpticalTransceiverObjects 1 }

raisecomOpticalTransceiverInfoTable OBJECT-TYPE
    SYNTAX      SEQUENCE OF RaisecomOpticalTransceiverInfoEntry
    MAX-ACCESS  not-accessible
    STATUS      current
    DESCRIPTION
        "Information about the transceiver in each pluggable port."
    ::= { raisecomOpticalTransceiverInfoGroup 1 }

raisecomOpticalTransceiverInfoEntry OBJECT-TYPE
    SYNTAX      RaisecomOpticalTransceiverInfoEntry
    MAX-ACCESS  not-accessible
    STATUS      current
    DESCRIPTION
        "Transceiver in one port."
    INDEX       { raisecomOpticalTransceiverInfoIfIndex }
    ::= { raisecomOpticalTransceiverInfoTable 1 }

RaisecomOpticalTransceiverInfoEntry ::= SEQUENCE {
    raisecomOpticalTransceiverType                  INTEGER,
    raisecomOpticalTransceiverConnectorType         INTEGER,
    raisecomOpticalTransceiverVendorName            OCTET STRING,
    raisecomOpticalTransceiverVendorPN              OCTET STRING,
    raisecomOpticalTransceiverVendorSN              OCTET STRING,
    raisecomOpticalTransceiverMediaType             INTEGER,
    raisecomOpticalTransceiverTransmissionDistance  Integer32,
    raisecomOpticalTransceiverAbility               Unsigned32,
    raisecomOpticalTransceiverDDM                   INTEGER,
    raisecomOpticalTransceiverCalibrationType       INTEGER,
    raisecomOpticalTransceiverRSSI                  INTEGER,
    raisecomOpticalTransceiverVendorRev             OCTET STRING,
    raisecomOpticalTransceiverBRMax                 Integer32,
    raisecomOpticalTransceiverBRMin                 Integer32,
    raisecomOpticalTransceiverWavelengthContrl      INTEGER,
    raisecomOpticalTransceiverWavelength            Integer32,
    raisecomOpticalTransceiverWaveTolerance         Integer32,
    raisecomOpticalTransceiverCompatibility         OCTET STRING,
    raisecomOpticalTransceiverPowerDissipation      INTEGER,
    raisecomOpticalTransceiverCDR                   INTEGER,
    raisecomOpticalTransceiverRefClock              INTEGER,
    raisecomOpticalTransceiverTransmitterType       INTEGER,
    raisecomOpticalTransceiverCooled                INTEGER,
    raisecomOpticalTransceiverTunalbe               INTEGER,
    raisecomOpticalTransceiverDetectorType          INTEGER,
    raisecomOpticalTransceiverLineLoopBack          INTEGER,
    raisecomOpticalTransceiverXFILoopBack           INTEGER,
    raisecomOpticalTransceiverVps                   INTEGER,
    raisecomOpticalTransceiverTxDis                 INTEGER,
    raisecomOpticalTransceiverStandby               INTEGER,
    raisecomOpticalTransceiverInVpsLowPower         INTEGER,
    raisecomOpticalTransceiverOutVpsLowPower        INTEGER,
    raisecomOpticalTransceiverFEC                   INTEGER,
    raisecomOpticalTransceiverCMU                   INTEGER,
    raisecomOpticalTransceiverInfoIfIndex           Integer32
}

raisecomOpticalTransceiverInfoIfIndex OBJECT-TYPE
    SYNTAX      Integer32 (1..2147483647)
    MAX-ACCESS  not-accessible
    STATUS      current
    DESCRIPTION
        "ifIndex of the port (IF-MIB ifIndex). Defined locally to keep
         this module self-contained."
    ::= { raisecomOpticalTransceiverInfoEntry 100 }

raisecomOpticalTransceiverType OBJECT-TYPE
    SYNTAX      INTEGER { unknown(1), gbic(2), soldered(3), sfp(4), xbi(5), xenpak(6), xfp(7), xff(8), xfpE(9), xpak(10), x2(11), sfpj(12) }
    MAX-ACCESS  read-only
    STATUS      current
    DESCRIPTION
        "Physical type of the transceiver."
    ::= { raisecomOpticalTransceiverInfoEntry 1 }

raisecomOpticalTransceiverConnectorType OBJECT-TYPE
    SYNTAX      INTEGER { unknown(0), sc(1), db9(2), hssdc(3), bncTnc(4), fiberCoaxialHead(5), fiberJack(6), lc(7), mtRj(8), mu(9), sg(10), fiberPigtail(11), mpoParallelOptic(12), hssdcII(20), copper(21), rj45(22) }
    MAX-ACCESS  read-only
    STATUS      current
    DESCRIPTION
        "Connector type."
    ::= { raisecomOpticalTransceiverInfoEntry 2 }

raisecomOpticalTransceiverVendorName OBJECT-TYPE
    SYNTAX      OCTET STRING (SIZE (0..32))
    MAX-ACCESS  read-only
    STATUS      current
    DESCRIPTION
        "Vendor name (space padded)."
    ::= { raisecomOpticalTransceiverInfoEntry 3 }

raisecomOpticalTransceiverVendorPN OBJECT-TYPE
    SYNTAX      OCTET STRING (SIZE (0..32))
    MAX-ACCESS  read-only
    STATUS      current
    DESCRIPTION
        "Vendor part number (space padded)."
    ::= { raisecomOpticalTransceiverInfoEntry 4 }

raisecomOpticalTransceiverVendorSN OBJECT-TYPE
    SYNTAX      OCTET STRING (SIZE (0..32))
    MAX-ACCESS  read-only
    STATUS      current
    DESCRIPTION
        "Vendor serial number (space padded)."
    ::= { raisecomOpticalTransceiverInfoEntry 5 }

raisecomOpticalTransceiverMediaType OBJECT-TYPE
    SYNTAX      INTEGER { singleMode(1), multiModeE50(2), multiMode50(3), multiMode625(4), copper(5), singleModeKm(6), multiModeOM3(7) }
    MAX-ACCESS  read-only
    STATUS      current
    DESCRIPTION
        "Fiber or cable type."
    ::= { raisecomOpticalTransceiverInfoEntry 6 }

raisecomOpticalTransceiverTransmissionDistance OBJECT-TYPE
    SYNTAX      Integer32
    UNITS       "meters"
    MAX-ACCESS  read-only
    STATUS      current
    DESCRIPTION
        "Maximum transmission distance."
    ::= { raisecomOpticalTransceiverInfoEntry 7 }

raisecomOpticalTransceiverAbility OBJECT-TYPE
    SYNTAX      Unsigned32
    MAX-ACCESS  read-only
    STATUS      current
    DESCRIPTION
        "Bit mask of the DDM parameters the module supports."
    ::= { raisecomOpticalTransceiverInfoEntry 8 }

raisecomOpticalTransceiverDDM OBJECT-TYPE
    SYNTAX      INTEGER { support(1), notSupport(2) }
    MAX-ACCESS  read-only
    STATUS      current
    DESCRIPTION
        "Whether the module supports digital diagnostics."
    ::= { raisecomOpticalTransceiverInfoEntry 9 }

raisecomOpticalTransceiverCalibrationType OBJECT-TYPE
    SYNTAX      INTEGER { unknown(1), internal(2), external(3) }
    MAX-ACCESS  read-only
    STATUS      current
    DESCRIPTION
        "DDM calibration type."
    ::= { raisecomOpticalTransceiverInfoEntry 10 }

raisecomOpticalTransceiverRSSI OBJECT-TYPE
    SYNTAX      INTEGER { support(1), notSupport(2) }
    MAX-ACCESS  read-only
    STATUS      current
    DESCRIPTION
        "Whether the module supports RSSI."
    ::= { raisecomOpticalTransceiverInfoEntry 11 }

raisecomOpticalTransceiverVendorRev OBJECT-TYPE
    SYNTAX      OCTET STRING (SIZE (0..16))
    MAX-ACCESS  read-only
    STATUS      current
    DESCRIPTION
        "Vendor revision."
    ::= { raisecomOpticalTransceiverInfoEntry 12 }

raisecomOpticalTransceiverBRMax OBJECT-TYPE
    SYNTAX      Integer32
    UNITS       "Mbps"
    MAX-ACCESS  read-only
    STATUS      current
    DESCRIPTION
        "Maximum bit rate."
    ::= { raisecomOpticalTransceiverInfoEntry 13 }

raisecomOpticalTransceiverBRMin OBJECT-TYPE
    SYNTAX      Integer32
    UNITS       "Mbps"
    MAX-ACCESS  read-only
    STATUS      current
    DESCRIPTION
        "Minimum bit rate."
    ::= { raisecomOpticalTransceiverInfoEntry 14 }

raisecomOpticalTransceiverWavelengthContrl OBJECT-TYPE
    SYNTAX      INTEGER { support(1), notSupport(2) }
    MAX-ACCESS  read-only
    STATUS      current
    DESCRIPTION
        "Whether wavelength control is supported."
    ::= { raisecomOpticalTransceiverInfoEntry 15 }

raisecomOpticalTransceiverWavelength OBJECT-TYPE
    SYNTAX      Integer32
    UNITS       "nm"
    MAX-ACCESS  read-only
    STATUS      current
    DESCRIPTION
        "Nominal laser wavelength. The published MIB says picometres;
         software 3.60.311 (ROS 5.2.1) returns nanometres (e.g. 1310)."
    ::= { raisecomOpticalTransceiverInfoEntry 16 }

raisecomOpticalTransceiverWaveTolerance OBJECT-TYPE
    SYNTAX      Integer32
    MAX-ACCESS  read-only
    STATUS      current
    DESCRIPTION
        "Wavelength tolerance. The published MIB types this OCTET STRING;
         software 3.60.311 (ROS 5.2.1) returns INTEGER."
    ::= { raisecomOpticalTransceiverInfoEntry 17 }

raisecomOpticalTransceiverCompatibility OBJECT-TYPE
    SYNTAX      OCTET STRING (SIZE (0..32))
    MAX-ACCESS  read-only
    STATUS      current
    DESCRIPTION
        "Compatibility code, e.g. 10GBASE-SR."
    ::= { raisecomOpticalTransceiverInfoEntry 18 }

raisecomOpticalTransceiverPowerDissipation OBJECT-TYPE
    SYNTAX      INTEGER { unknown(0), p1W5(1), p2W5(2), p3W5(3), exceed(4) }
    MAX-ACCESS  read-only
    STATUS      current
    DESCRIPTION
        "Power class. software 3.60.311 (ROS 5.2.1) returns unknown(0)
         for SFPs."
    ::= { raisecomOpticalTransceiverInfoEntry 19 }

raisecomOpticalTransceiverCDR OBJECT-TYPE
    SYNTAX      INTEGER { support(1), notSupport(2) }
    MAX-ACCESS  read-only
    STATUS      current
    DESCRIPTION
        "Whether the module has clock and data recovery."
    ::= { raisecomOpticalTransceiverInfoEntry 20 }

raisecomOpticalTransceiverRefClock OBJECT-TYPE
    SYNTAX      INTEGER { required(1), notRequired(2) }
    MAX-ACCESS  read-only
    STATUS      current
    DESCRIPTION
        "Whether a reference clock is required."
    ::= { raisecomOpticalTransceiverInfoEntry 21 }

raisecomOpticalTransceiverTransmitterType OBJECT-TYPE
    SYNTAX      INTEGER { vcsel850nm(1), vcsel1310nm(2), vcsel1550nm(3), fp1310nm(4), dfb1310nm(5), dfb1550nm(6), eml1310nm(7), eml1550nm(8), copperOthers(9) }
    MAX-ACCESS  read-only
    STATUS      current
    DESCRIPTION
        "Transmitter technology."
    ::= { raisecomOpticalTransceiverInfoEntry 22 }

raisecomOpticalTransceiverCooled OBJECT-TYPE
    SYNTAX      INTEGER { cooled(1), uncooled(2) }
    MAX-ACCESS  read-only
    STATUS      current
    DESCRIPTION
        "Whether the laser is cooled."
    ::= { raisecomOpticalTransceiverInfoEntry 24 }

raisecomOpticalTransceiverTunalbe OBJECT-TYPE
    SYNTAX      INTEGER { tunable(1), untunable(2) }
    MAX-ACCESS  read-only
    STATUS      current
    DESCRIPTION
        "Whether the laser is tunable."
    ::= { raisecomOpticalTransceiverInfoEntry 25 }

raisecomOpticalTransceiverDetectorType OBJECT-TYPE
    SYNTAX      INTEGER { pin(1), apd(2) }
    MAX-ACCESS  read-only
    STATUS      current
    DESCRIPTION
        "Receiver detector type."
    ::= { raisecomOpticalTransceiverInfoEntry 26 }

raisecomOpticalTransceiverLineLoopBack OBJECT-TYPE
    SYNTAX      INTEGER { support(1), notSupport(2) }
    MAX-ACCESS  read-only
    STATUS      current
    DESCRIPTION
        "Line loopback support."
    ::= { raisecomOpticalTransceiverInfoEntry 27 }

raisecomOpticalTransceiverXFILoopBack OBJECT-TYPE
    SYNTAX      INTEGER { support(1), notSupport(2) }
    MAX-ACCESS  read-only
    STATUS      current
    DESCRIPTION
        "XFI loopback support."
    ::= { raisecomOpticalTransceiverInfoEntry 28 }

raisecomOpticalTransceiverVps OBJECT-TYPE
    SYNTAX      INTEGER { support(1), notSupport(2) }
    MAX-ACCESS  read-only
    STATUS      current
    DESCRIPTION
        "Variable power supply support."
    ::= { raisecomOpticalTransceiverInfoEntry 29 }

raisecomOpticalTransceiverTxDis OBJECT-TYPE
    SYNTAX      INTEGER { support(1), notSupport(2) }
    MAX-ACCESS  read-only
    STATUS      current
    DESCRIPTION
        "Transmitter disable support."
    ::= { raisecomOpticalTransceiverInfoEntry 30 }

raisecomOpticalTransceiverStandby OBJECT-TYPE
    SYNTAX      INTEGER { support(1), notSupport(2) }
    MAX-ACCESS  read-only
    STATUS      current
    DESCRIPTION
        "Standby mode support."
    ::= { raisecomOpticalTransceiverInfoEntry 31 }

raisecomOpticalTransceiverInVpsLowPower OBJECT-TYPE
    SYNTAX      INTEGER { support(1), notSupport(2) }
    MAX-ACCESS  read-only
    STATUS      current
    DESCRIPTION
        "Low power mode support inside VPS."
    ::= { raisecomOpticalTransceiverInfoEntry 32 }

raisecomOpticalTransceiverOutVpsLowPower OBJECT-TYPE
    SYNTAX      INTEGER { support(1), notSupport(2) }
    MAX-ACCESS  read-only
    STATUS      current
    DESCRIPTION
        "Low power mode support outside VPS."
    ::= { raisecomOpticalTransceiverInfoEntry 33 }

raisecomOpticalTransceiverFEC OBJECT-TYPE
    SYNTAX      INTEGER { support(1), notSupport(2) }
    MAX-ACCESS  read-only
    STATUS      current
    DESCRIPTION
        "Forward error correction support."
    ::= { raisecomOpticalTransceiverInfoEntry 34 }

raisecomOpticalTransceiverCMU OBJECT-TYPE
    SYNTAX      INTEGER { support(1), notSupport(2) }
    MAX-ACCESS  read-only
    STATUS      current
    DESCRIPTION
        "Clock multiplier unit support."
    ::= { raisecomOpticalTransceiverInfoEntry 35 }

raisecomOpticalTransceiverDDMGroup OBJECT IDENTIFIER ::= { raisecomOpticalTransceiverObjects 2 }

raisecomOpticalTransceiverDDMTable OBJECT-TYPE
    SYNTAX      SEQUENCE OF RaisecomOpticalTransceiverDDMEntry
    MAX-ACCESS  not-accessible
    STATUS      current
    DESCRIPTION
        "Digital diagnostics of each transceiver parameter. Rows of
         modules without DDM support contain zeros."
    ::= { raisecomOpticalTransceiverDDMGroup 1 }

raisecomOpticalTransceiverDDMEntry OBJECT-TYPE
    SYNTAX      RaisecomOpticalTransceiverDDMEntry
    MAX-ACCESS  not-accessible
    STATUS      current
    DESCRIPTION
        "One monitored parameter of one transceiver."
    INDEX       { raisecomOpticalTransceiverDDMIfIndex, raisecomOpticalTransceiverParameterType }
    ::= { raisecomOpticalTransceiverDDMTable 1 }

RaisecomOpticalTransceiverDDMEntry ::= SEQUENCE {
    raisecomOpticalTransceiverParameterType           OpticalParameterType,
    raisecomOpticalTransceiverParameterValue          OpticalParameterValue,
    raisecomOpticalTransceiverParamHighAlarmThresh    OpticalParameterValue,
    raisecomOpticalTransceiverParamHighWarningThresh  OpticalParameterValue,
    raisecomOpticalTransceiverParamLowAlarmThresh     OpticalParameterValue,
    raisecomOpticalTransceiverParamLowWarningThresh   OpticalParameterValue,
    raisecomOpticalTransceiverParamAlarmStatus        INTEGER,
    raisecomOpticalTransceiverParamAlarmLastValue     OpticalParameterValue,
    raisecomOpticalTransceiverParamAlarmLastChange    TimeTicks,
    raisecomOpticalTransceiverDDM15MinValidIntervals  Unsigned32,
    raisecomOpticalTransceiverDDM24HrValidIntervals   Unsigned32,
    raisecomOpticalTransceiverDDMValidStatus          INTEGER,
    raisecomOpticalTransceiverDDMIfIndex              Integer32
}

raisecomOpticalTransceiverDDMIfIndex OBJECT-TYPE
    SYNTAX      Integer32 (1..2147483647)
    MAX-ACCESS  not-accessible
    STATUS      current
    DESCRIPTION
        "ifIndex of the port (IF-MIB ifIndex). Defined locally to keep
         this module self-contained."
    ::= { raisecomOpticalTransceiverDDMEntry 100 }

raisecomOpticalTransceiverParameterType OBJECT-TYPE
    SYNTAX      OpticalParameterType
    MAX-ACCESS  not-accessible
    STATUS      current
    DESCRIPTION
        "Monitored parameter."
    ::= { raisecomOpticalTransceiverDDMEntry 1 }

raisecomOpticalTransceiverParameterValue OBJECT-TYPE
    SYNTAX      OpticalParameterValue
    MAX-ACCESS  read-only
    STATUS      current
    DESCRIPTION
        "Current value."
    ::= { raisecomOpticalTransceiverDDMEntry 2 }

raisecomOpticalTransceiverParamHighAlarmThresh OBJECT-TYPE
    SYNTAX      OpticalParameterValue
    MAX-ACCESS  read-only
    STATUS      current
    DESCRIPTION
        "High alarm threshold."
    ::= { raisecomOpticalTransceiverDDMEntry 3 }

raisecomOpticalTransceiverParamHighWarningThresh OBJECT-TYPE
    SYNTAX      OpticalParameterValue
    MAX-ACCESS  read-only
    STATUS      current
    DESCRIPTION
        "High warning threshold."
    ::= { raisecomOpticalTransceiverDDMEntry 4 }

raisecomOpticalTransceiverParamLowAlarmThresh OBJECT-TYPE
    SYNTAX      OpticalParameterValue
    MAX-ACCESS  read-only
    STATUS      current
    DESCRIPTION
        "Low alarm threshold."
    ::= { raisecomOpticalTransceiverDDMEntry 5 }

raisecomOpticalTransceiverParamLowWarningThresh OBJECT-TYPE
    SYNTAX      OpticalParameterValue
    MAX-ACCESS  read-only
    STATUS      current
    DESCRIPTION
        "Low warning threshold."
    ::= { raisecomOpticalTransceiverDDMEntry 6 }

raisecomOpticalTransceiverParamAlarmStatus OBJECT-TYPE
    SYNTAX      INTEGER { unknown(0), normal(1), highAlarm(2), highWarning(3), lowAlarm(4), lowWarning(5) }
    MAX-ACCESS  read-only
    STATUS      current
    DESCRIPTION
        "Current threshold state."
    ::= { raisecomOpticalTransceiverDDMEntry 7 }

raisecomOpticalTransceiverParamAlarmLastValue OBJECT-TYPE
    SYNTAX      OpticalParameterValue
    MAX-ACCESS  read-only
    STATUS      current
    DESCRIPTION
        "Value when the last alarm was raised."
    ::= { raisecomOpticalTransceiverDDMEntry 8 }

raisecomOpticalTransceiverParamAlarmLastChange OBJECT-TYPE
    SYNTAX      TimeTicks
    MAX-ACCESS  read-only
    STATUS      current
    DESCRIPTION
        "sysUpTime when the alarm status last changed."
    ::= { raisecomOpticalTransceiverDDMEntry 9 }

raisecomOpticalTransceiverDDM15MinValidIntervals OBJECT-TYPE
    SYNTAX      Unsigned32 (0..96)
    MAX-ACCESS  read-only
    STATUS      current
    DESCRIPTION
        "Number of valid 15-minute history intervals."
    ::= { raisecomOpticalTransceiverDDMEntry 10 }

raisecomOpticalTransceiverDDM24HrValidIntervals OBJECT-TYPE
    SYNTAX      Unsigned32 (0..7)
    MAX-ACCESS  read-only
    STATUS      current
    DESCRIPTION
        "Number of valid 24-hour history intervals."
    ::= { raisecomOpticalTransceiverDDMEntry 11 }

raisecomOpticalTransceiverDDMValidStatus OBJECT-TYPE
    SYNTAX      INTEGER { unknown(0), valid(1), invalid(2) }
    MAX-ACCESS  read-only
    STATUS      current
    DESCRIPTION
        "Whether the current value is valid."
    ::= { raisecomOpticalTransceiverDDMEntry 12 }

-- Objects of RAISECOM-DEVICE-MIB

raisecomDeviceMIB OBJECT IDENTIFIER ::= { iscomSwitch 1 }

raisecomDeviceInfo OBJECT IDENTIFIER ::= { raisecomDeviceMIB 1 }

raisecomDeviceSoftwareVersion OBJECT-TYPE
    SYNTAX      DisplayString
    MAX-ACCESS  read-only
    STATUS      current
    DESCRIPTION
        "Software version, e.g. 3.60.311(Compiled Mar 25 2020 18:40:44).
         Reconstructed from data returned by ISCOM2624G-4GE-PWR-AC,
         software 3.60.311 (ROS 5.2.1); Raisecom publishes no MIB for
         this object."
    ::= { raisecomDeviceInfo 1 }

raisecomDeviceHardwareVersion OBJECT-TYPE
    SYNTAX      DisplayString
    MAX-ACCESS  read-only
    STATUS      current
    DESCRIPTION
        "Hardware version, e.g. A.01. Reconstructed from data returned by
         ISCOM2624G-4GE-PWR-AC, software 3.60.311 (ROS 5.2.1); Raisecom
         publishes no MIB for this object."
    ::= { raisecomDeviceInfo 2 }

raisecomDevicePortNumber OBJECT-TYPE
    SYNTAX      Integer32
    MAX-ACCESS  read-only
    STATUS      current
    DESCRIPTION
        "Number of interfaces (equals ifNumber on the reference device).
         Reconstructed from data returned by ISCOM2624G-4GE-PWR-AC,
         software 3.60.311 (ROS 5.2.1); Raisecom publishes no MIB for
         this object."
    ::= { raisecomDeviceInfo 5 }

raisecomDeviceMacAddress OBJECT-TYPE
    SYNTAX      MacAddress
    MAX-ACCESS  read-only
    STATUS      current
    DESCRIPTION
        "System MAC address. Reconstructed from data returned by
         ISCOM2624G-4GE-PWR-AC, software 3.60.311 (ROS 5.2.1); Raisecom
         publishes no MIB for this object."
    ::= { raisecomDeviceInfo 9 }

raisecomDeviceBootromVersion OBJECT-TYPE
    SYNTAX      DisplayString
    MAX-ACCESS  read-only
    STATUS      current
    DESCRIPTION
        "Bootrom version. Reconstructed from data returned by
         ISCOM2624G-4GE-PWR-AC, software 3.60.311 (ROS 5.2.1); Raisecom
         publishes no MIB for this object."
    ::= { raisecomDeviceInfo 13 }

raisecomDeviceSerialNumber OBJECT-TYPE
    SYNTAX      DisplayString
    MAX-ACCESS  read-only
    STATUS      current
    DESCRIPTION
        "Serial number. Reconstructed from data returned by
         ISCOM2624G-4GE-PWR-AC, software 3.60.311 (ROS 5.2.1); Raisecom
         publishes no MIB for this object."
    ::= { raisecomDeviceInfo 14 }

raisecomDeviceDescription OBJECT-TYPE
    SYNTAX      DisplayString
    MAX-ACCESS  read-only
    STATUS      current
    DESCRIPTION
        "Model and software version, e.g. ISCOM2624G-4GE-PWR-AC 3.60.311.
         Reconstructed from data returned by ISCOM2624G-4GE-PWR-AC,
         software 3.60.311 (ROS 5.2.1); Raisecom publishes no MIB for
         this object."
    ::= { raisecomDeviceInfo 16 }

raisecomDeviceVendor OBJECT-TYPE
    SYNTAX      DisplayString
    MAX-ACCESS  read-only
    STATUS      current
    DESCRIPTION
        "Vendor short name. Reconstructed from data returned by
         ISCOM2624G-4GE-PWR-AC, software 3.60.311 (ROS 5.2.1); Raisecom
         publishes no MIB for this object."
    ::= { raisecomDeviceInfo 17 }

raisecomDeviceManufacturer OBJECT-TYPE
    SYNTAX      DisplayString
    MAX-ACCESS  read-only
    STATUS      current
    DESCRIPTION
        "Manufacturer full name. Reconstructed from data returned by
         ISCOM2624G-4GE-PWR-AC, software 3.60.311 (ROS 5.2.1); Raisecom
         publishes no MIB for this object."
    ::= { raisecomDeviceInfo 18 }

raisecomDeviceModelName OBJECT-TYPE
    SYNTAX      DisplayString
    MAX-ACCESS  read-only
    STATUS      current
    DESCRIPTION
        "Model name, e.g. ISCOM2624G-4GE-PWR-AC. Reconstructed from data
         returned by ISCOM2624G-4GE-PWR-AC, software 3.60.311 (ROS
         5.2.1); Raisecom publishes no MIB for this object."
    ::= { raisecomDeviceInfo 19 }

-- Objects of RAISECOM-PORT-MIB

raisecomPortMIB OBJECT IDENTIFIER ::= { iscomSwitch 20 }

raisecomPortObjects OBJECT IDENTIFIER ::= { raisecomPortMIB 1 }

raisecomPortTable OBJECT-TYPE
    SYNTAX      SEQUENCE OF RaisecomPortEntry
    MAX-ACCESS  not-accessible
    STATUS      current
    DESCRIPTION
        "Per-port settings."
    ::= { raisecomPortObjects 1 }

raisecomPortEntry OBJECT-TYPE
    SYNTAX      RaisecomPortEntry
    MAX-ACCESS  not-accessible
    STATUS      current
    DESCRIPTION
        "Settings of one port."
    INDEX       { raisecomPortIfIndex }
    ::= { raisecomPortTable 1 }

RaisecomPortEntry ::= SEQUENCE {
    raisecomPortDescription  DisplayString,
    raisecomPortIfIndex      Integer32
}

raisecomPortIfIndex OBJECT-TYPE
    SYNTAX      Integer32 (1..2147483647)
    MAX-ACCESS  not-accessible
    STATUS      current
    DESCRIPTION
        "ifIndex of the port (IF-MIB ifIndex). Defined locally to keep
         this module self-contained."
    ::= { raisecomPortEntry 100 }

raisecomPortDescription OBJECT-TYPE
    SYNTAX      DisplayString
    MAX-ACCESS  read-only
    STATUS      current
    DESCRIPTION
        "Description configured on the port (ROS leaves IF-MIB ifAlias
         empty). Reconstructed from data returned by ISCOM2624G-4GE-PWR-
         AC, software 3.60.311 (ROS 5.2.1); Raisecom publishes no MIB for
         this object."
    ::= { raisecomPortEntry 2 }

-- Objects of RAISECOM-POE-MIB

raisecomPoeMIB OBJECT IDENTIFIER ::= { iscomSwitch 51 }

raisecomPoePortTable OBJECT-TYPE
    SYNTAX      SEQUENCE OF RaisecomPoePortEntry
    MAX-ACCESS  not-accessible
    STATUS      current
    DESCRIPTION
        "Per-port PoE measurements."
    ::= { raisecomPoeMIB 1 }

raisecomPoePortEntry OBJECT-TYPE
    SYNTAX      RaisecomPoePortEntry
    MAX-ACCESS  not-accessible
    STATUS      current
    DESCRIPTION
        "PoE measurements of one port, indexed like pethPsePortTable (PSE
         group, port ifIndex)."
    INDEX       { raisecomPoePortGroupIndex, raisecomPoePortIfIndex }
    ::= { raisecomPoePortTable 1 }

RaisecomPoePortEntry ::= SEQUENCE {
    raisecomPoePortPeakPower        Gauge32,
    raisecomPoePortPower            Gauge32,
    raisecomPoePortPowerInstant     Gauge32,
    raisecomPoePortVoltage          Gauge32,
    raisecomPoePortCurrent          Gauge32,
    raisecomPoePortPowerLimit       Gauge32,
    raisecomPoePortAdminStatus      EnableVar,
    raisecomPoePortForcePower       EnableVar,
    raisecomPoePortScheduleProfile  Integer32,
    raisecomPoePortAliveCheck       EnableVar,
    raisecomPoePortAliveAction      INTEGER,
    raisecomPoePortRebootInterval   Integer32,
    raisecomPoePortLinktraceTrack   Integer32,
    raisecomPoePortOperStatus       EnableVar,
    raisecomPoePortGroupIndex       Integer32,
    raisecomPoePortIfIndex          Integer32
}

raisecomPoePortIfIndex OBJECT-TYPE
    SYNTAX      Integer32 (1..2147483647)
    MAX-ACCESS  not-accessible
    STATUS      current
    DESCRIPTION
        "ifIndex of the port (IF-MIB ifIndex). Defined locally to keep
         this module self-contained."
    ::= { raisecomPoePortEntry 101 }

raisecomPoePortGroupIndex OBJECT-TYPE
    SYNTAX      Integer32 (1..2147483647)
    MAX-ACCESS  not-accessible
    STATUS      current
    DESCRIPTION
        "PSE group, always 1 on single-PSE switches. Matches
         pethPsePortGroupIndex."
    ::= { raisecomPoePortEntry 100 }

raisecomPoePortPeakPower OBJECT-TYPE
    SYNTAX      Gauge32
    UNITS       "milliwatts"
    MAX-ACCESS  read-only
    STATUS      current
    DESCRIPTION
        "Highest power drawn on the port. Reconstructed from data
         returned by ISCOM2624G-4GE-PWR-AC, software 3.60.311 (ROS
         5.2.1); Raisecom publishes no MIB for this object."
    ::= { raisecomPoePortEntry 1 }

raisecomPoePortPower OBJECT-TYPE
    SYNTAX      Gauge32
    UNITS       "milliwatts"
    MAX-ACCESS  read-only
    STATUS      current
    DESCRIPTION
        "Power drawn by the powered device, smoothed (moving average of
         raisecomPoePortPowerInstant). Reconstructed from data returned
         by ISCOM2624G-4GE-PWR-AC, software 3.60.311 (ROS 5.2.1);
         Raisecom publishes no MIB for this object."
    ::= { raisecomPoePortEntry 2 }

raisecomPoePortPowerInstant OBJECT-TYPE
    SYNTAX      Gauge32
    UNITS       "milliwatts"
    MAX-ACCESS  read-only
    STATUS      current
    DESCRIPTION
        "Latest power sample, 100 mW resolution; this is the 'Output
         Power(mW)' column of CLI 'show poe interface'. Reconstructed
         from data returned by ISCOM2624G-4GE-PWR-AC, software 3.60.311
         (ROS 5.2.1); Raisecom publishes no MIB for this object."
    ::= { raisecomPoePortEntry 3 }

raisecomPoePortVoltage OBJECT-TYPE
    SYNTAX      Gauge32
    UNITS       "millivolts"
    MAX-ACCESS  read-only
    STATUS      current
    DESCRIPTION
        "Output voltage ('Output Voltage(mV)' in CLI). Reconstructed from
         data returned by ISCOM2624G-4GE-PWR-AC, software 3.60.311 (ROS
         5.2.1); Raisecom publishes no MIB for this object."
    ::= { raisecomPoePortEntry 4 }

raisecomPoePortCurrent OBJECT-TYPE
    SYNTAX      Gauge32
    UNITS       "milliamperes"
    MAX-ACCESS  read-only
    STATUS      current
    DESCRIPTION
        "Output current ('Output Current(mA)' in CLI). Reconstructed from
         data returned by ISCOM2624G-4GE-PWR-AC, software 3.60.311 (ROS
         5.2.1); Raisecom publishes no MIB for this object."
    ::= { raisecomPoePortEntry 5 }

raisecomPoePortPowerLimit OBJECT-TYPE
    SYNTAX      Gauge32
    UNITS       "milliwatts"
    MAX-ACCESS  read-only
    STATUS      current
    DESCRIPTION
        "Maximum power the port may deliver ('Max Power(mW)' in CLI, set
         with 'poe max-power'). Reconstructed from data returned by
         ISCOM2624G-4GE-PWR-AC, software 3.60.311 (ROS 5.2.1); Raisecom
         publishes no MIB for this object."
    ::= { raisecomPoePortEntry 6 }

raisecomPoePortAdminStatus OBJECT-TYPE
    SYNTAX      EnableVar
    MAX-ACCESS  read-only
    STATUS      current
    DESCRIPTION
        "Administrative PoE state of the port (CLI 'poe enable|disable',
         shown as 'POE administrator status'). 'poe disable' changes this
         column together with raisecomPoePortOperStatus and
         pethPsePortAdminEnable; it is taken as the administrative one
         because columns 7..14 all hold port settings. Reconstructed from
         data returned by ISCOM2624G-4GE-PWR-AC, software 3.60.311 (ROS
         5.2.1); Raisecom publishes no MIB for this object."
    ::= { raisecomPoePortEntry 7 }

raisecomPoePortForcePower OBJECT-TYPE
    SYNTAX      EnableVar
    MAX-ACCESS  read-only
    STATUS      current
    DESCRIPTION
        "Force power without PD detection (CLI 'poe force-power', shown
         as 'POE force-power status'). Reconstructed from data returned
         by ISCOM2624G-4GE-PWR-AC, software 3.60.311 (ROS 5.2.1);
         Raisecom publishes no MIB for this object."
    ::= { raisecomPoePortEntry 8 }

raisecomPoePortScheduleProfile OBJECT-TYPE
    SYNTAX      Integer32 (0..2147483647)
    MAX-ACCESS  read-only
    STATUS      current
    DESCRIPTION
        "PoE schedule profile bound to the port, 0 for none (CLI 'poe
         schedule profile', shown as 'POE schedule profile'). Inferred
         from the column position and the CLI field order; not verified.
         Reconstructed from data returned by ISCOM2624G-4GE-PWR-AC,
         software 3.60.311 (ROS 5.2.1); Raisecom publishes no MIB for
         this object."
    ::= { raisecomPoePortEntry 9 }

raisecomPoePortAliveCheck OBJECT-TYPE
    SYNTAX      EnableVar
    MAX-ACCESS  read-only
    STATUS      current
    DESCRIPTION
        "PD alive check (CLI 'poe alive check enable|disable', shown as
         'POE PD check status'). Mapping verified by changing the setting
         via CLI and observing this column. Reconstructed from data
         returned by ISCOM2624G-4GE-PWR-AC, software 3.60.311 (ROS
         5.2.1); Raisecom publishes no MIB for this object."
    ::= { raisecomPoePortEntry 10 }

raisecomPoePortAliveAction OBJECT-TYPE
    SYNTAX      INTEGER { none(0), reboot(1), rebootAlarm(2), alarm(3) }
    MAX-ACCESS  read-only
    STATUS      current
    DESCRIPTION
        "Action when the PD alive check fails (CLI 'poe alive action
         reboot|reboot-alarm|alarm', 'no poe alive action' gives none;
         shown as 'POE PD fail action', N/A for none). Mapping verified
         by changing the setting via CLI and observing this column.
         Reconstructed from data returned by ISCOM2624G-4GE-PWR-AC,
         software 3.60.311 (ROS 5.2.1); Raisecom publishes no MIB for
         this object."
    ::= { raisecomPoePortEntry 11 }

raisecomPoePortRebootInterval OBJECT-TYPE
    SYNTAX      Integer32 (0..2147483647)
    UNITS       "seconds"
    MAX-ACCESS  read-only
    STATUS      current
    DESCRIPTION
        "Power-off time when rebooting a failed PD (CLI 'poe reboot
         interval', shown as 'POE PD fail reboot interval'). Mapping
         verified by changing the setting via CLI and observing this
         column. Reconstructed from data returned by ISCOM2624G-4GE-PWR-
         AC, software 3.60.311 (ROS 5.2.1); Raisecom publishes no MIB for
         this object."
    ::= { raisecomPoePortEntry 12 }

raisecomPoePortLinktraceTrack OBJECT-TYPE
    SYNTAX      Integer32 (0..128)
    MAX-ACCESS  read-only
    STATUS      current
    DESCRIPTION
        "Track object the port follows, 0 for none (CLI 'poe linktrace
         track <1-128>', 'no poe linktrace' gives 0; shown as 'POE PD
         linktrace'). Mapping verified by changing the setting via CLI
         and observing this column. Reconstructed from data returned by
         ISCOM2624G-4GE-PWR-AC, software 3.60.311 (ROS 5.2.1); Raisecom
         publishes no MIB for this object."
    ::= { raisecomPoePortEntry 14 }

raisecomPoePortOperStatus OBJECT-TYPE
    SYNTAX      EnableVar
    MAX-ACCESS  read-only
    STATUS      current
    DESCRIPTION
        "Operational PoE state of the port (shown as 'POE operation
         status' / 'POE actual running status'; the two could not be told
         apart). Follows raisecomPoePortAdminStatus when PoE is disabled
         on the port. Reconstructed from data returned by ISCOM2624G-4GE-
         PWR-AC, software 3.60.311 (ROS 5.2.1); Raisecom publishes no MIB
         for this object."
    ::= { raisecomPoePortEntry 15 }

raisecomPoePseTable OBJECT-TYPE
    SYNTAX      SEQUENCE OF RaisecomPoePseEntry
    MAX-ACCESS  not-accessible
    STATUS      current
    DESCRIPTION
        "Per-PSE PoE totals."
    ::= { raisecomPoeMIB 2 }

raisecomPoePseEntry OBJECT-TYPE
    SYNTAX      RaisecomPoePseEntry
    MAX-ACCESS  not-accessible
    STATUS      current
    DESCRIPTION
        "Totals of one PSE."
    INDEX       { raisecomPoePseGroupIndex }
    ::= { raisecomPoePseTable 1 }

RaisecomPoePseEntry ::= SEQUENCE {
    raisecomPoePseAveragePower           Gauge32,
    raisecomPoePsePeakPower              Gauge32,
    raisecomPoePseLegacyDetection        EnableVar,
    raisecomPoePseTemperatureProtection  EnableVar,
    raisecomPoePsePower                  Gauge32,
    raisecomPoePseGroupIndex             Integer32
}

raisecomPoePseGroupIndex OBJECT-TYPE
    SYNTAX      Integer32 (1..2147483647)
    MAX-ACCESS  not-accessible
    STATUS      current
    DESCRIPTION
        "PSE group, always 1 on single-PSE switches. Matches
         pethMainPseGroupIndex."
    ::= { raisecomPoePseEntry 100 }

raisecomPoePseAveragePower OBJECT-TYPE
    SYNTAX      Gauge32
    UNITS       "milliwatts"
    MAX-ACCESS  read-only
    STATUS      current
    DESCRIPTION
        "Total power delivered, averaged by the switch ('Average
         Power(mW)' in CLI 'show poe pse'). The instantaneous total in
         whole watts is pethMainPseConsumptionPower ('Output Power(W)').
         Reconstructed from data returned by ISCOM2624G-4GE-PWR-AC,
         software 3.60.311 (ROS 5.2.1); Raisecom publishes no MIB for
         this object."
    ::= { raisecomPoePseEntry 1 }

raisecomPoePsePeakPower OBJECT-TYPE
    SYNTAX      Gauge32
    UNITS       "milliwatts"
    MAX-ACCESS  read-only
    STATUS      current
    DESCRIPTION
        "Highest total power delivered ('Peak Power(mW)' in CLI).
         Reconstructed from data returned by ISCOM2624G-4GE-PWR-AC,
         software 3.60.311 (ROS 5.2.1); Raisecom publishes no MIB for
         this object."
    ::= { raisecomPoePseEntry 2 }

raisecomPoePsePower OBJECT-TYPE
    SYNTAX      Gauge32
    UNITS       "watts"
    MAX-ACCESS  read-only
    STATUS      current
    DESCRIPTION
        "Power budget of the PSE ('Wattage Rating(W)' in CLI,
         pethMainPsePower). Reconstructed from data returned by
         ISCOM2624G-4GE-PWR-AC, software 3.60.311 (ROS 5.2.1); Raisecom
         publishes no MIB for this object."
    ::= { raisecomPoePseEntry 8 }

raisecomPoePseLegacyDetection OBJECT-TYPE
    SYNTAX      EnableVar
    MAX-ACCESS  read-only
    STATUS      current
    DESCRIPTION
        "Detection of legacy (pre-802.3af) powered devices (CLI 'poe
         legacy enable|disable', shown as 'PSE legacy detection').
         Mapping verified by changing the setting via CLI and observing
         this column. Reconstructed from data returned by ISCOM2624G-4GE-
         PWR-AC, software 3.60.311 (ROS 5.2.1); Raisecom publishes no MIB
         for this object."
    ::= { raisecomPoePseEntry 3 }

raisecomPoePseTemperatureProtection OBJECT-TYPE
    SYNTAX      EnableVar
    MAX-ACCESS  read-only
    STATUS      current
    DESCRIPTION
        "Over-temperature protection of the PSE (CLI 'poe temperature-
         protection enable|disable', shown as 'Switch temperature-
         protection'). Mapping verified by changing the setting via CLI
         and observing this column. Reconstructed from data returned by
         ISCOM2624G-4GE-PWR-AC, software 3.60.311 (ROS 5.2.1); Raisecom
         publishes no MIB for this object."
    ::= { raisecomPoePseEntry 5 }

END
